import os, sys, glob, traceback, importlib, re, math

_log_dir = os.getenv("FREECAD_LOG_DIR") or os.path.join(
    os.getenv("FREECAD_STEP_OUT") or os.getcwd(), "_logs"
)
os.makedirs(_log_dir, exist_ok=True)
log_path = os.getenv("FREECAD_LOG_PATH") or os.path.join(_log_dir, "freecad_log.txt")
_log_mode = "a" if os.getenv("FREECAD_LOG_APPEND", "").strip() in ("1", "true", "yes") else "w"
log_file = open(log_path, _log_mode, encoding="utf-8")
sys.stdout, sys.stderr = log_file, log_file
if _log_mode == "a":
    print("\n--- FREECAD sesión (append) ---\n")

import FreeCAD as App
import FreeCADGui
import ImportGui
import Part
import importDXF

try:
    prefs = App.ParamGet("User parameter:BaseApp/Preferences/Mod/Draft")
    prefs.SetBool("TeighaCheck", False)
    prefs.SetBool("UseTeigha", False)
    prefs.SetBool("dxfShowDialog", False)

    prefs_step = App.ParamGet("User parameter:BaseApp/Preferences/Mod/Import/hSTEP")
    prefs_step.SetBool("ExportFreeEdges", True)
    prefs_step.SetBool("ExportFreeWires", True)
    prefs_step.SetInt("WriteSchema", 2)
except Exception:
    pass

def silenciar_ventanas_emergentes():
    for mod in ['PySide6', 'PySide2', 'PyQt6', 'PyQt5']:
        try:
            QtWidgets = importlib.import_module(f"{mod}.QtWidgets")
            QtWidgets.QMessageBox.information = lambda *a, **kw: None
            QtWidgets.QMessageBox.warning = lambda *a, **kw: None
            QtWidgets.QMessageBox.critical = lambda *a, **kw: None
            QtWidgets.QMessageBox.question = lambda *a, **kw: 65536
            QtWidgets.QDialog.exec = lambda self, *a, **kw: 0
            if hasattr(QtWidgets.QDialog, 'exec_'):
                QtWidgets.QDialog.exec_ = lambda self, *a, **kw: 0
            return
        except Exception:
            pass

silenciar_ventanas_emergentes()

try:
    _main_win = FreeCADGui.getMainWindow()
    if _main_win:
        _main_win.hide()
except Exception:
    pass

def _load_mark_edges_from_json(json_path):
    """Segmentos MARK desde sidecar (DXF slim); evita importar miles de líneas en FreeCAD."""
    import json

    edges = []
    with open(json_path, "r", encoding="utf-8") as fh:
        payload = json.load(fh)
    for seg in payload.get("segments", []):
        if not seg or len(seg) < 4:
            continue
        try:
            p1 = App.Vector(float(seg[0]), float(seg[1]), 0.0)
            p2 = App.Vector(float(seg[2]), float(seg[3]), 0.0)
            line = Part.makeLine(p1, p2)
            if line and not line.isNull():
                edges.extend(list(line.Edges))
        except Exception:
            pass
    return edges

PER_PIECE_MARK_THRESHOLD = 6000


def _should_imprint_per_piece(mark_count: int) -> bool:
    """Modo C: sólidos primero, marcas por pieza (hojas densas / DXF slim)."""
    mode = _env_str("FREECAD_PHASE_MODE", "AUTO").strip().upper()
    if mode in ("PER_PIECE", "PIECE", "SOLIDS_THEN_MARKS"):
        return True
    if mode in ("PLATE", "LEGACY"):
        return False
    if os.getenv("FREECAD_MARK_JSON", "").strip():
        return True
    return int(mark_count) >= PER_PIECE_MARK_THRESHOLD


def _normalize_mark_mode(raw: str) -> str:
    """ENGRAVE=ranuras (cut); IMPRINT=legacy fuse de caras 0-grosor."""
    m = str(raw or "ENGRAVE").strip().upper()
    if m in ("CUT", "GROOVE", "ENGRAVE", "BOOLEAN", "CARVE"):
        return "ENGRAVE"
    if m in ("IMPRINT", "FUSE", "LEGACY"):
        return "IMPRINT"
    return "ENGRAVE"


def _mark_mode_applies_to_solid(mark_mode: str) -> bool:
    return _normalize_mark_mode(mark_mode) in ("ENGRAVE", "IMPRINT")


def _edge_xy_endpoints(edge):
    try:
        vs = list(edge.Vertexes)
    except Exception:
        return None
    if len(vs) < 2:
        return None
    return vs[0].Point, vs[-1].Point


def _build_mark_groove_tool(edge, z_bottom: float, height: float, width: float):
    """Prisma rectangular a lo largo de un segmento MARK (unidades XY del DXF)."""
    if width <= 1e-9 or height <= 1e-9:
        return None
    ends = _edge_xy_endpoints(edge)
    if not ends:
        return None
    p1, p2 = ends
    dx = float(p2.x - p1.x)
    dy = float(p2.y - p1.y)
    length = math.hypot(dx, dy)
    if length < 1e-9:
        return None
    pad = min(width * 0.2, length * 0.08)
    box = Part.makeBox(length + 2.0 * pad, width, height)
    box.translate(App.Vector(-pad, -0.5 * width, 0.0))
    box.rotate(App.Vector(0, 0, 0), App.Vector(0, 0, 1), math.degrees(math.atan2(dy, dx)))
    box.translate(App.Vector(float(p1.x), float(p1.y), float(z_bottom)))
    return box


def _build_mark_ribbons(
    mark_edges_m,
    vector_marcas_z,
    vec_up,
    mark_mode,
    *,
    width: float = 0.02,
):
    ribbons = []
    if not mark_edges_m:
        return ribbons
    mode = _normalize_mark_mode(mark_mode)
    z0 = float(getattr(vector_marcas_z, "z", 0.0))
    h = abs(float(getattr(vec_up, "z", vec_up)))
    if h <= 1e-12:
        return ribbons
    for edge in mark_edges_m:
        try:
            if mode == "ENGRAVE":
                tool = _build_mark_groove_tool(edge, z0, h, float(width))
                if tool is not None and not tool.isNull():
                    ribbons.append(tool)
            else:
                e_rib = edge.copy()
                e_rib.translate(vector_marcas_z)
                rib = e_rib.extrude(vec_up)
                if rib and not rib.isNull():
                    ribbons.append(rib)
        except Exception:
            pass
    return ribbons


def _apply_imprint_ribbons_on_solid(solid, ribbons, *, chunk=100, mark_mode="ENGRAVE"):
    if not ribbons or solid is None or solid.isNull():
        return solid
    mode = _normalize_mark_mode(mark_mode)
    out = solid
    for i in range(0, len(ribbons), chunk):
        bloque = ribbons[i : i + chunk]
        try:
            comp_rib = Part.makeCompound(bloque)
            if mode == "ENGRAVE":
                temp_shape = out.cut(comp_rib)
            else:
                temp_shape = out.generalFuse([comp_rib])[0]
            temp_shape = _solo_solidos(temp_shape)
            if (
                temp_shape
                and not temp_shape.isNull()
                and float(getattr(temp_shape, "Volume", 0.0) or 0.0) > 1e-6
            ):
                out = temp_shape
        except Exception:
            for rib in bloque:
                try:
                    if mode == "ENGRAVE":
                        temp_shape = out.cut(rib)
                    else:
                        temp_shape = out.generalFuse([rib])[0]
                    temp_shape = _solo_solidos(temp_shape)
                    if (
                        temp_shape
                        and not temp_shape.isNull()
                        and float(getattr(temp_shape, "Volume", 0.0) or 0.0) > 1e-6
                    ):
                        out = temp_shape
                except Exception:
                    pass
    return _solo_solidos(out)


def _marks_for_piece(mark_edges_m, piece_bbox, margin=1.0):
    """Asigna marcas a la pieza cuyo bbox contiene el centro de cada arista."""
    if not mark_edges_m or piece_bbox is None:
        return []
    out = []
    xmin = float(piece_bbox.XMin) - margin
    xmax = float(piece_bbox.XMax) + margin
    ymin = float(piece_bbox.YMin) - margin
    ymax = float(piece_bbox.YMax) + margin
    for edge in mark_edges_m:
        try:
            bb = edge.BoundBox
            cx = (float(bb.XMin) + float(bb.XMax)) * 0.5
            cy = (float(bb.YMin) + float(bb.YMax)) * 0.5
            if xmin <= cx <= xmax and ymin <= cy <= ymax:
                out.append(edge)
        except Exception:
            pass
    return out


def _env_float(name: str, default: float) -> float:
    try:
        return float(os.getenv(name, str(default)))
    except Exception:
        return default

def _env_str(name: str, default: str) -> str:
    try:
        v = os.getenv(name, default)
        return str(v) if v is not None else default
    except: return default

def _export_format() -> str:
    return _env_str("FREECAD_EXPORT_FORMAT", "step").strip().lower()

def _export_extension() -> str:
    fmt = _export_format()
    return ".igs" if fmt in ("iges", "igs") else ".step"

def _export_label() -> str:
    return "IGES" if _export_extension() == ".igs" else "STEP"

def _is_iges_export() -> bool:
    return _export_format() in ("iges", "igs")

def _cad_base_from_dxf_name(name: str) -> str:
    step_base = name
    for prefix in ("_joined_", "_slim_"):
        if step_base.startswith(prefix):
            step_base = step_base[len(prefix) :]
            break
    idx = step_base.upper().find("W.O.")
    if idx != -1:
        step_base = step_base[idx:].strip()
    return step_base

_NESTING_THK_IN_RE = re.compile(r"NESTING[_\s-]*([0-9]*\.?[0-9]+)", re.IGNORECASE)
_SWO_THK_IN_RE = re.compile(r"SWO[-\s]*\d+[_\s-]+([0-9]*\.?[0-9]+)", re.IGNORECASE)


def _thk_mm_from_dxf_name(path_or_name: str, default_mm: float) -> float:
    """Calibre desde NESTING_<pulgadas>_… o SWO-NNN_<pulgadas>_… → mm."""
    name = os.path.basename(str(path_or_name or ""))
    m = _NESTING_THK_IN_RE.search(name)
    if not m:
        m = _SWO_THK_IN_RE.search(name)
    if not m:
        return float(default_mm)
    try:
        return float(m.group(1)) * 25.4
    except Exception:
        return float(default_mm)

def _configure_export_units():
    unit = _env_str("FREECAD_EXPORT_LINEAR_UNIT", "").strip().upper()
    fmt = _export_format()
    is_iges = fmt in ("iges", "igs")
    if not unit:
        unit = "MM" if is_iges else "IN"
    occt_unit = "MM" if unit == "MM" else "IN"
    try:
        h_part = App.ParamGet("User parameter:BaseApp/Preferences/Mod/Part")
        if is_iges:
            h_part.SetInt("UnitIges", 0)
            try:
                h_part.GetGroup("IGES").SetInt("Unit", 0)
            except Exception:
                pass
        else:
            h_part.SetInt("Unit", 2)
            try:
                h_part.SetInt("UnitStep", 2)
            except Exception:
                pass
    except Exception as exc:
        print(f"WARN Part unit prefs: {exc}")

    key = f"write.{'iges' if is_iges else 'step'}.unit"
    ok = False
    for static in _interface_static_candidates():
        for val in ([occt_unit] + (["INCH"] if occt_unit == "IN" else [])):
            try:
                static.SetCVal(key, val)
                print(f"OCCT {key}={val}")
                ok = True
                break
            except Exception:
                continue
        if ok:
            break
    if not ok:
        try:
            from OCC.Core.Interface import Interface_Static as OccStatic

            for val in ([occt_unit] + (["INCH"] if occt_unit == "IN" else [])):
                try:
                    OccStatic.SetCVal(key, val)
                    print(f"OCCT {key}={val}")
                    ok = True
                    break
                except Exception:
                    continue
        except Exception:
            pass
    if not ok:
        print(f"WARN: no se pudo fijar {key}={occt_unit}")
    print(f"Unidades export {('IGES' if is_iges else 'STEP')}: {unit}")

def _interface_static_candidates():
    out = []
    try:
        from OCC.Core.Interface import Interface_Static as OccStatic
        out.append(OccStatic)
    except Exception:
        pass
    try:
        if hasattr(Part, "Interface_Static"):
            out.append(Part.Interface_Static)
    except Exception:
        pass
    try:
        from Part.App import Interface
        out.append(Interface.Interface_Static)
    except Exception:
        pass
    return out

def _normalize_material_kind(raw):
    u = str(raw or "").strip().upper()
    if u in ("CU", "COBRE", "COPPER"):
        return "copper"
    return "steel"

def _material_kind_for_export(perfil=None):
    env_raw = os.getenv("FREECAD_MATERIAL", "").strip()
    if env_raw:
        return _normalize_material_kind(env_raw)
    if perfil and perfil.get("name") == "ARGA_COBRE_LARGOS":
        return "copper"
    return "steel"

def _appearance_preset(kind):
    if kind == "copper":
        return {
            "diffuse": (0.78, 0.48, 0.22),
            "ambient": (0.32, 0.20, 0.09),
            "specular": (0.95, 0.78, 0.45),
            "shininess": 0.90,
        }
    return {
        "diffuse": (0.58, 0.60, 0.63),
        "ambient": (0.22, 0.23, 0.25),
        "specular": (0.90, 0.90, 0.92),
        "shininess": 0.72,
    }

def _apply_part_appearance(view_obj, kind):
    """Apariencia metálica para STEP AP214 (Inventor lee diffuse + specular)."""
    if not view_obj:
        return
    preset = _appearance_preset(kind)
    try:
        view_obj.ShapeAppearance = App.Material(
            DiffuseColor=preset["diffuse"],
            AmbientColor=preset["ambient"],
            SpecularColor=preset["specular"],
            EmissiveColor=(0.0, 0.0, 0.0),
            Shininess=float(preset["shininess"]),
            Transparency=0.0,
        )
        return
    except Exception:
        pass
    try:
        d = preset["diffuse"]
        view_obj.ShapeColor = (d[0], d[1], d[2], 0.0)
    except Exception:
        pass

def _collect_closed_wires(obj):
    wires = []
    if not hasattr(obj, "Shape") or obj.Shape.isNull(): return wires
    try:
        for w in obj.Shape.Wires:
            if w and w.isClosed(): wires.append(w)
    except: pass
    if not wires:
        try:
            for g in Part.sortEdges(obj.Shape.Edges):
                w = Part.Wire(g)
                if w.isClosed(): wires.append(w)
        except: pass
    return wires

def _collect_edges(obj):
    edges = []
    if not hasattr(obj, "Shape") or obj.Shape.isNull(): return edges
    try:
        for e in obj.Shape.Edges: edges.append(e)
    except: pass
    return edges

def _wire_signature(w):
    try:
        bb = w.BoundBox
        area = 0.0
        cx = (bb.XMin + bb.XMax) * 0.5
        cy = (bb.YMin + bb.YMax) * 0.5
        try:
            f = Part.Face(w)
            if not f.isNull():
                area = abs(float(f.Area))
                cm = f.CenterOfMass
                cx, cy = float(cm.x), float(cm.y)
        except Exception:
            pass
        return (
            round(bb.XMin, 2), round(bb.YMin, 2),
            round(bb.XMax, 2), round(bb.YMax, 2),
            round(area, 2),
            round(cx, 2), round(cy, 2),
        )
    except Exception:
        return None

def _dedupe_wires(wires):
    out = []
    seen = set()
    for w in wires or []:
        sig = _wire_signature(w)
        if sig is None or sig in seen:
            continue
        seen.add(sig)
        out.append(w)
    return out

def _filter_cu_bar_marker_edges(edges):
    """Quita la línea vertical de inicio de barra si quedó mezclada en CUT_CU (DXF viejos)."""
    if not edges:
        return []
    max_y = 0.0
    for e in edges:
        try:
            for v in e.Vertexes:
                max_y = max(max_y, float(v.Point.y))
        except Exception:
            pass
    if max_y <= 1.0:
        return list(edges)

    kept = []
    for e in edges:
        try:
            v1 = e.Vertexes[0].Point
            v2 = e.Vertexes[-1].Point
            if abs(v1.x) <= 0.05 and abs(v2.x) <= 0.05:
                ymin = min(float(v1.y), float(v2.y))
                ymax = max(float(v1.y), float(v2.y))
                span = ymax - ymin
                if ymin <= 0.05 and ymax >= max_y - 0.5 and span >= max_y * 0.85:
                    continue
        except Exception:
            pass
        kept.append(e)
    return kept

def _collect_closed_wires_merged(objects, isolate_per_object=False):
    """Une LINE/ARC sueltos del export nest (1:1) en wires cerrados vía Part.sortEdges."""
    objs = [o for o in (objects or []) if o is not None]
    if not objs:
        return []

    merged = []
    for obj in objs:
        merged.extend(_collect_closed_wires(obj))

    if isolate_per_object:
        for obj in objs:
            edges = _filter_cu_bar_marker_edges(_collect_edges(obj))
            if not edges:
                continue
            try:
                for group in Part.sortEdges(edges):
                    try:
                        w = Part.Wire(group)
                        if w.isClosed():
                            merged.append(w)
                    except Exception:
                        pass
            except Exception:
                pass
        return _dedupe_wires(merged)

    all_edges = []
    for obj in objs:
        all_edges.extend(_collect_edges(obj))

    all_edges = _filter_cu_bar_marker_edges(all_edges)

    if all_edges:
        try:
            for group in Part.sortEdges(all_edges):
                try:
                    w = Part.Wire(group)
                    if w.isClosed():
                        merged.append(w)
                except Exception:
                    pass
        except Exception:
            pass

    return _dedupe_wires(merged)

def _iter_layer_group_nodes(doc):
    """Recorre grupos de capa DXF a cualquier profundidad (CUT_CU suele ir bajo Layers)."""
    skip_labels = {"LAYERS", "LAYERCONTAINER"}

    def _walk(obj):
        if not hasattr(obj, "Group") or not obj.Group:
            return
        lbl = str(obj.Label or "").upper().strip()
        if lbl and lbl not in skip_labels:
            yield obj
        for child in obj.Group:
            yield from _walk(child)

    for obj in getattr(doc, "Objects", []):
        yield from _walk(obj)

def _layer_label_for_obj(obj, *, skip_labels=None):
    """Capa DXF del objeto (sube por InList hasta el grupo de capa)."""
    skip = skip_labels or {"LAYERS", "LAYERCONTAINER"}
    seen = set()
    stack = [obj]
    while stack:
        cur = stack.pop()
        cid = id(cur)
        if cid in seen:
            continue
        seen.add(cid)
        lbl = str(getattr(cur, "Label", "") or "").upper().strip()
        if lbl and lbl not in skip and hasattr(cur, "Group") and cur.Group:
            return lbl
        for parent in getattr(cur, "InList", []) or []:
            stack.append(parent)
    return str(getattr(obj, "Label", "") or "").upper().strip()

def _iter_geometry_objects(doc):
    for obj in getattr(doc, "Objects", []):
        if not hasattr(obj, "Shape") or obj.Shape.isNull():
            continue
        if hasattr(obj, "Group") and obj.Group:
            continue
        yield obj

def _iter_cut_cu_objects(doc, perfil):
    """Objetos con geometría CUT_CU, incluyendo INSERT/block refs importados."""
    if perfil.get("name") != "ARGA_COBRE_LARGOS":
        yield from _iter_geometry_objects(doc)
        return
    seen = set()
    for obj in getattr(doc, "Objects", []):
        if not hasattr(obj, "Shape") or obj.Shape.isNull():
            continue
        lbl = _layer_label_for_obj(obj)
        if not _label_matches_any(lbl, {"CUT_CU"}):
            continue
        oid = id(obj)
        if oid in seen:
            continue
        seen.add(oid)
        if hasattr(obj, "Group") and obj.Group:
            for child in obj.Group:
                if hasattr(child, "Shape") and not child.Shape.isNull():
                    yield child
            continue
        yield obj

def _bucket_add(bucket: list, seen: set, obj) -> None:
    if obj is None:
        return
    oid = id(obj)
    if oid in seen:
        return
    seen.add(oid)
    bucket.append(obj)

def _classify_obj(obj, lbl, perfil, outer_objs, inner_objs, plate_objs, mixed_objs, mark_e, seen):
    if _label_matches_any(lbl, perfil.get("mark", set())):
        mark_e.extend(_collect_edges(obj))
    elif _label_matches_any(lbl, perfil.get("mixed_contour", set())):
        _bucket_add(mixed_objs, seen, obj)
    elif _label_matches_any(lbl, perfil.get("outer", set())):
        _bucket_add(outer_objs, seen, obj)
    elif _label_matches_any(lbl, perfil.get("inner", set())):
        _bucket_add(inner_objs, seen, obj)
    elif _label_matches_any(lbl, perfil.get("plate", {"PLATE"})):
        _bucket_add(plate_objs, seen, obj)

def _collect_contours_from_doc(doc, perfil):
    outer_objs, inner_objs, plate_objs, mixed_objs, mark_e = [], [], [], [], []
    seen = set()
    from_groups = set()
    classified_names = set()

    for group in _iter_layer_group_nodes(doc):
        lbl = str(group.Label or "").upper()
        for child in group.Group or []:
            from_groups.add(id(child))
            classified_names.add(getattr(child, "Name", None))
            _classify_obj(child, lbl, perfil, outer_objs, inner_objs, plate_objs, mixed_objs, mark_e, seen)

    for obj in _iter_cut_cu_objects(doc, perfil) if perfil.get("name") == "ARGA_COBRE_LARGOS" else _iter_geometry_objects(doc):
        if id(obj) in from_groups or getattr(obj, "Name", None) in classified_names:
            continue
        lbl = _layer_label_for_obj(obj)
        _classify_obj(obj, lbl, perfil, outer_objs, inner_objs, plate_objs, mixed_objs, mark_e, seen)

    isolate_cu = perfil.get("name") == "ARGA_COBRE_LARGOS"
    outer_w = _collect_closed_wires_merged(outer_objs, isolate_per_object=isolate_cu)
    inner_w = _collect_closed_wires_merged(inner_objs)
    plate_w = _collect_closed_wires_merged(plate_objs)
    mixed_contours = _collect_closed_wires_merged(mixed_objs)
    return outer_w, inner_w, plate_w, mark_e, mixed_contours

def _aplicar_offset_2d(wires, offset_val):
    if abs(offset_val) < 0.001: return wires
    new_wires = []
    for w in wires:
        try:
            off_shape = w.makeOffset2D(offset_val, join=2)
            for nw in off_shape.Wires:
                if nw.isClosed(): new_wires.append(nw)
        except Exception: new_wires.append(w)
    return new_wires if new_wires else wires

def _reconstruir_circulos_estricto(wire):
    if not wire.isClosed(): return wire
    bb = wire.BoundBox
    dx = bb.XMax - bb.XMin
    dy = bb.YMax - bb.YMin
    if dx < 1e-3 or dy < 1e-3: return wire
    if abs(dx - dy) / max(dx, dy) > 0.05: return wire
    radius = (dx + dy) / 4.0
    center = App.Vector(bb.XMin + dx/2.0, bb.YMin + dy/2.0, bb.ZMin)
    for v in wire.Vertexes:
        dist = (v.Point - center).Length
        if abs(dist - radius) > (radius * 0.08): return wire
    try:
        circ_edge = Part.makeCircle(radius, center, App.Vector(0,0,1))
        return Part.Wire(circ_edge)
    except: return wire

def _pick_biggest_wire(wires):
    if not wires: return None
    best = None
    best_area = -1.0
    for w in wires:
        bb = w.BoundBox
        area = (bb.XMax - bb.XMin) * (bb.YMax - bb.YMin)
        if area > best_area:
            best_area = area
            best = w
    return best

LAYER_LIBRARY = [
    {
        # Biblioteca dedicada para DXF de Robot Laser + Mini Nest con capas numéricas.
        # Capa 1 trae todo: contornos externos, internos e islas.
        "name": "ROBOT_LASER_MINI_NUMERIC_V2",
        "outer": set(),
        "inner": set(),
        "mixed_contour": {"1"},
        "mark": {"4"},
        "plate": {"6"},
        "predicate": lambda layers: bool(layers) and set(layers).issubset({"1", "4", "6"}),
    },
    {
        # Cobre CU-LARGOS legacy: CUT_CU (DXF antiguos). Nest actual usa CUT_OUTER.
        "name": "ARGA_COBRE_LARGOS",
        "outer": {"CUT_CU"},
        "inner": {"CUT_INNER", "INNER", "INTER"},
        "mark": {"MARK", "ETCH", "TEXT"},
        "plate": {"PLATE"},
        "mixed_contour": set(),
        "predicate": lambda layers: (
            any(str(l).upper().strip() == "CUT_CU" for l in layers)
            and not any(str(l).upper().strip() == "CUT_OUTER" for l in layers)
        ),
    },
    {
        "name": "ARGA_NESTING_STD",
        "outer": {"CUT_OUTER", "OUTER", "EXTER"},
        "inner": {"CUT_INNER", "INNER", "INTER"},
        "mark": {"MARK", "ETCH", "TEXT"},
        "plate": {"PLATE"},
        "mixed_contour": set(),
        "predicate": lambda layers: True,  # perfil base
    },
]

def _resolver_perfil_capas(layers_presentes):
    for prof in LAYER_LIBRARY:
        try:
            if prof["predicate"](layers_presentes):
                return prof
        except Exception:
            continue
    return LAYER_LIBRARY[-1]

def _label_matches_any(lbl, keys):
    if not keys:
        return False
    lbl = (lbl or "").strip().upper()
    if not lbl:
        return False
    tokens = [t for t in re.split(r"[^A-Z0-9_.-]+", lbl) if t]
    for k in keys:
        ku = str(k).strip().upper()
        if not ku:
            continue
        if ku.isdigit():
            if lbl == ku or ku in tokens:
                return True
        else:
            # CUT_CU no debe empatar CUT_OUTER (substring legacy).
            if ku == "CUT_CU":
                if lbl == "CUT_CU" or "CUT_CU" in tokens:
                    return True
                continue
            if lbl == ku or ku in tokens:
                return True
            if ku in lbl:
                return True
    return False

def _collect_labels_from_doc(doc):
    labels = []
    for obj in getattr(doc, "Objects", []):
        try:
            labels.append(str(getattr(obj, "Label", "") or ""))
        except Exception:
            pass
        try:
            if hasattr(obj, "Group") and obj.Group:
                for c in obj.Group:
                    labels.append(str(getattr(c, "Label", "") or ""))
        except Exception:
            pass
    return labels

def _layer_has_geometry(doc, layer_name: str) -> bool:
    """True si la capa tiene al menos un objeto con Shape en el documento importado."""
    target = str(layer_name or "").strip().upper()
    if not target:
        return False
    for group in _iter_layer_group_nodes(doc):
        lbl = str(group.Label or "").upper()
        if not _label_matches_any(lbl, {target}):
            continue
        for child in group.Group or []:
            if hasattr(child, "Shape") and not child.Shape.isNull():
                return True
    for obj in _iter_geometry_objects(doc):
        lbl = _layer_label_for_obj(obj)
        if _label_matches_any(lbl, {target}):
            return True
    return False

def _resolver_perfil_desde_labels(labels, doc=None):
    # 1) Forzar perfil numérico cuando aparezcan capas 1/4/6 en etiquetas de FreeCAD.
    has1 = any(_label_matches_any(lbl, {"1"}) for lbl in labels)
    has4 = any(_label_matches_any(lbl, {"4"}) for lbl in labels)
    has6 = any(_label_matches_any(lbl, {"6"}) for lbl in labels)
    if has1 and (has4 or has6):
        for prof in LAYER_LIBRARY:
            if prof["name"] == "ROBOT_LASER_MINI_NUMERIC_V2":
                return prof

    has_cut_cu = any(_label_matches_any(lbl, {"CUT_CU"}) for lbl in labels)
    has_cut_outer = any(_label_matches_any(lbl, {"CUT_OUTER"}) for lbl in labels)
    if has_cut_cu and doc is not None:
        has_cut_cu = _layer_has_geometry(doc, "CUT_CU")
    if has_cut_cu and not has_cut_outer:
        for prof in LAYER_LIBRARY:
            if prof["name"] == "ARGA_COBRE_LARGOS":
                return prof

    # 2) Fallback a detección previa.
    norm = set()
    for lbl in labels:
        u = str(lbl or "").strip().upper()
        if u:
            norm.add(u)
    return _resolver_perfil_capas(norm)

def _clasificar_wires_paridad(wires):
    """
    Clasifica contornos mezclados por profundidad de anidamiento:
    - profundidad par  -> material (outer / islas)
    - profundidad impar -> corte (inner)
    """
    if not wires:
        return [], []

    wf = []
    for w in wires:
        try:
            f = Part.Face(w)
            if not f.isNull() and f.Area > 1e-7:
                wf.append((w, f))
        except Exception:
            pass

    if not wf:
        return [], []

    material = []
    cortes = []
    for i, (w_i, f_i) in enumerate(wf):
        try:
            p_i = f_i.CenterOfMass
        except Exception:
            material.append(w_i)
            continue

        depth = 0
        area_i = abs(float(getattr(f_i, "Area", 0.0) or 0.0))
        for j, (_w_j, f_j) in enumerate(wf):
            if i == j:
                continue
            try:
                area_j = abs(float(getattr(f_j, "Area", 0.0) or 0.0))
                if area_j <= area_i:
                    continue
                if f_j.isInside(p_i, 1e-6, True):
                    depth += 1
            except Exception:
                pass

        if depth % 2 == 0:
            material.append(w_i)
        else:
            cortes.append(w_i)

    return material, cortes

# ==========================================================
# TU FUNCIÓN CLAVE PARA EVITAR SURFACE BODIES
# ==========================================================
def _solo_solidos(shape):
    """
    Devuelve SOLO sólidos (sin shells/surfaces).
    Esto evita que el STEP exporte Surface Bodies en Inventor/PQart.
    """
    if not shape or getattr(shape, "isNull", lambda: True)():
        return shape
    try:
        sols = list(shape.Solids)
    except Exception:
        sols = []

    if not sols:
        return shape  # no hay sólidos; devolvemos tal cual

    if len(sols) == 1:
        return sols[0]

    try:
        return Part.makeCompound(sols)
    except Exception:
        return sols[0]


def _bbox_of_shapes(shapes):
    bb = None
    for sh in shapes or []:
        if sh is None or getattr(sh, "isNull", lambda: True)():
            continue
        try:
            b = sh.BoundBox
        except Exception:
            continue
        if bb is None:
            bb = b
        else:
            bb.add(b)
    return bb


def _cyptube_rotate_length_to_z(shape, pivot):
    """Nest (largo en X) → CypTube (largo en +Z, sección en XY)."""
    out = shape.rotate(pivot, App.Vector(0, 1, 0), 90)
    return out if out is not None else shape


def _normalize_shape_to_origin(shape):
    bb = shape.BoundBox
    delta = App.Vector(-bb.XMin, -bb.YMin, -bb.ZMin)
    out = shape.translate(delta)
    return out if out is not None else shape


def _edges_from_wires(wires):
    edges = []
    for w in wires or []:
        try:
            for e in w.Edges:
                edges.append(e)
        except Exception:
            pass
    return edges


def _imprint_edges_on_bar(solid, edges, shift, top_z, rib_h_mm, *, chunk=100, width=0.02):
    """Graba aristas en la cara superior del sólido (contornos / marcas)."""
    if not edges or solid is None or solid.isNull():
        return solid
    shifted = []
    for e in edges:
        try:
            ec = e.copy()
            ec.translate(shift)
            shifted.append(ec)
        except Exception:
            pass
    if not shifted:
        return solid
    vector_marcas_z = App.Vector(0, 0, float(top_z))
    vec_up = App.Vector(0, 0, float(rib_h_mm))
    mark_mode = _normalize_mark_mode(_env_str("FREECAD_MARK_MODE", "ENGRAVE"))
    ribbons = _build_mark_ribbons(
        shifted, vector_marcas_z, vec_up, mark_mode, width=float(width)
    )
    if not ribbons:
        return solid
    try:
        out = _apply_imprint_ribbons_on_solid(
            solid, ribbons, chunk=chunk, mark_mode=mark_mode
        )
        return _solo_solidos(out)
    except Exception:
        return solid


def _build_cyptube_flatbar_iges(
    doc,
    name,
    outer_w,
    inner_w,
    plate_w,
    laser_edges,
    mark_edges,
    thk_mm,
    off_x,
    off_y,
    off_z,
    material_kind,
):
    """
    IGES para CypTube (barra plana) — un solo sólido extruido:
    - Largo en +Z; sección ancho×espesor en XY.
    - Agujeros interiores: corte booleano.
    - Contornos láser y marcas: imprint en cara superior (no wires sueltos).
    CypTube/Inventor fallan si el IGES es compound de sólido + curvas flotantes.
    """
    ref = list(plate_w or outer_w or inner_w)
    if not ref and not laser_edges:
        print(f"[{name}] IGES CypTube: sin geometría de referencia.")
        return []

    bb = _bbox_of_shapes(ref + list(laser_edges or []))
    if bb is None or bb.XLength < 0.5 or bb.YLength < 0.5:
        print(f"[{name}] IGES CypTube: bbox inválido.")
        return []

    shift = App.Vector(
        -bb.XMin + float(off_x),
        -bb.YMin + float(off_y),
        float(off_z),
    )
    pivot = App.Vector(shift.x, shift.y, shift.z)
    bar_len = float(bb.XLength)
    bar_wid = float(bb.YLength)
    bar_thk = float(thk_mm)
    mark_z_offset = _env_float("FREECAD_MARK_Z_OFFSET", -0.5)
    mark_top_z = shift.z + bar_thk + mark_z_offset
    cut_rib_h = _env_float("FREECAD_CYPTUBE_CUT_RIB_H", 0.25)
    mark_rib_h = _env_float("FREECAD_MARK_RIB_H", 1.0)

    n_marks = len(mark_edges or [])
    cut_edges = _edges_from_wires(list(outer_w) + list(inner_w)) + list(laser_edges or [])
    print(
        f"[{name}] IGES CypTube: stock {bar_len:.2f}×{bar_wid:.2f}×{bar_thk:.2f} mm, "
        f"eje largo→+Z | sólido único | {len(cut_edges)} aristas corte, {n_marks} marcas"
    )

    stock = Part.makeBox(bar_len, bar_wid, bar_thk)
    stock.translate(shift)
    result = stock

    hole_tools = []
    for iw in inner_w or []:
        try:
            iw2 = iw.copy()
            iw2.translate(shift)
            tool = Part.Face(iw2).extrude(App.Vector(0, 0, bar_thk + 0.4))
            tool.translate(App.Vector(0, 0, -0.2))
            hole_tools.append(tool)
        except Exception:
            pass
    if hole_tools:
        try:
            result = result.cut(Part.makeCompound(hole_tools))
            result = _solo_solidos(result)
        except Exception as exc:
            print(f"[{name}] WARN IGES CypTube: perforado inner omitido ({exc})")

    if cut_edges:
        print(f"[{name}] IGES CypTube: imprint {len(cut_edges)} aristas de corte...")
        cut_w = _env_float("FREECAD_CYPTUBE_CUT_WIDTH", 0.015)
        result = _imprint_edges_on_bar(
            result, cut_edges, shift, mark_top_z, cut_rib_h, chunk=150, width=cut_w
        )

    if mark_edges:
        mark_w = _env_float("FREECAD_MARK_WIDTH", 0.02)
        if n_marks <= PER_PIECE_MARK_THRESHOLD:
            print(f"[{name}] IGES CypTube: imprint {n_marks} marcas...")
            result = _imprint_edges_on_bar(
                result, mark_edges, shift, mark_top_z, mark_rib_h, chunk=100, width=mark_w
            )
        else:
            print(
                f"[{name}] IGES CypTube: {n_marks} marcas → imprint por bloques "
                f"(umbral {PER_PIECE_MARK_THRESHOLD})"
            )
            result = _imprint_edges_on_bar(
                result, mark_edges, shift, mark_top_z, mark_rib_h, chunk=80, width=mark_w
            )

    result = _cyptube_rotate_length_to_z(result, pivot)
    bb_rot = result.BoundBox
    print(
        f"[{name}] IGES CypTube bbox post-rot: "
        f"X={bb_rot.XLength:.2f} Y={bb_rot.YLength:.2f} Z={bb_rot.ZLength:.2f} mm"
    )
    result = _normalize_shape_to_origin(result)
    try:
        result = result.removeSplitter()
    except Exception:
        pass
    result = _solo_solidos(result)

    feat = doc.addObject("Part::Feature", "CYPTUBE_FLATBAR")
    feat.Label = "CypTube_Barra"
    feat.Shape = result
    _apply_part_appearance(feat.ViewObject, material_kind)

    return [feat]


def _collect_cut_outer_edges(doc):
    """Aristas de capa CUT_OUTER (guillotinas y cortes láser abiertos en cobre)."""
    edges = []
    for obj in getattr(doc, "Objects", []):
        lbl = _layer_label_for_obj(obj)
        targets = []
        if hasattr(obj, "Group") and obj.Group:
            for child in obj.Group:
                if hasattr(child, "Shape") and not child.Shape.isNull():
                    targets.append(child)
        elif hasattr(obj, "Shape") and not obj.Shape.isNull():
            targets.append(obj)
        for target in targets:
            tlbl = _layer_label_for_obj(target)
            if _label_matches_any(tlbl, {"CUT_OUTER"}) or _label_matches_any(lbl, {"CUT_OUTER"}):
                edges.extend(_collect_edges(target))
    return edges


def procesar_dxf(dxf_path, step_out_dir, thk_mm, scale, origen_tipo, off_x, off_y, off_z):
    name = os.path.splitext(os.path.basename(dxf_path))[0]
    thk_mm = _thk_mm_from_dxf_name(dxf_path, thk_mm)
    print(f"[{name}] FREECAD_THK_MM efectivo: {float(thk_mm):.4f}")

    # Queremos conservar el identificador útil para seguimiento:
    # ejemplo:
    # NESTING_0.105_W.O. 11 X8-H27  ->  W.O. 11 X8-H27
    step_base = _cad_base_from_dxf_name(name)
    cad_ext = _export_extension()
    cad_label = _export_label()
    out_step = os.path.join(step_out_dir, f"{step_base}{cad_ext}")
    print(f"[{name}] Nombre {cad_label} usado: {step_base}{cad_ext}")

    if os.getenv("FREECAD_SKIP_EXISTING", "1").strip().lower() not in ("0", "false", "no"):
        try:
            if os.path.isfile(out_step) and os.path.getsize(out_step) > 512:
                if os.path.getmtime(out_step) >= os.path.getmtime(dxf_path):
                    print(f"[{name}] SKIP: {cad_label} vigente ya existe -> {out_step}")
                    return
        except Exception:
            pass

    doc = App.newDocument(f"DXF_{name}")
    import_path = os.getenv("FREECAD_DXF_IMPORT", dxf_path).strip() or dxf_path
    if import_path != dxf_path:
        print(f"[{name}] Import DXF slim (sin MARK): {import_path}")
    importDXF.insert(import_path, doc.Name)
    doc.recompute()

    labels_doc = _collect_labels_from_doc(doc)
    perfil = _resolver_perfil_desde_labels(labels_doc, doc)
    print(f"[{name}] Perfil de capas activo: {perfil['name']}")
    outer_w, inner_w, plate_w, mark_e, mixed_contours = _collect_contours_from_doc(doc, perfil)
    mark_json = os.getenv("FREECAD_MARK_JSON", "").strip()
    if mark_json and os.path.isfile(mark_json):
        import json as _json
        with open(mark_json, "r", encoding="utf-8") as _mj:
            _mark_payload = _json.load(_mj)
        expected_segments = int(_mark_payload.get("segment_count") or 0)
        mark_e = _load_mark_edges_from_json(mark_json)
        print(
            f"[{name}] Marcas sidecar 1:1: {len(mark_e)} aristas "
            f"(esperadas {expected_segments}, entidades MARK {_mark_payload.get('mark_entities', '?')})"
        )
        if expected_segments and len(mark_e) < expected_segments:
            print(
                f"[{name}] ERROR: pérdida de marcas en sidecar "
                f"({len(mark_e)}/{expected_segments}). No se exporta STEP incompleto."
            )
            App.closeDocument(doc.Name)
            return

    if mixed_contours:
        mats, cuts = _clasificar_wires_paridad(mixed_contours)
        outer_w.extend(mats)
        inner_w.extend(cuts)
        print(f"[{name}] MIXED contour layer -> material:{len(mats)} cortes:{len(cuts)}")

    print(f"\n[{name}] -> OUTER: {len(outer_w)}, INNER: {len(inner_w)}, PLATE: {len(plate_w)}, LINEAS MARCAJE: {len(mark_e)}")

    if not outer_w and not plate_w:
        print(f"[{name}] SKIP: sin contornos OUTER ni PLATE utilizables")
        App.closeDocument(doc.Name)
        return

    plasma_offset = _env_float("FREECAD_PLASMA_OFFSET", 0.0)
    if abs(plasma_offset) > 0.001:
        outer_w = _aplicar_offset_2d(outer_w, plasma_offset)
        inner_w = _aplicar_offset_2d(inner_w, -plasma_offset)
        plate_w = _aplicar_offset_2d(plate_w, plasma_offset) if plate_w else plate_w


    if abs(scale - 1.0) > 1e-9:
        m = App.Matrix()
        m.A11, m.A22, m.A33 = scale, scale, scale
        outer_w = [w.transformGeometry(m) for w in outer_w]
        inner_w = [w.transformGeometry(m) for w in inner_w]
        plate_w = [w.transformGeometry(m) for w in plate_w]
        mark_e = [e.transformGeometry(m) for e in mark_e]

    if _is_iges_export():
        laser_e = _collect_cut_outer_edges(doc)
        if abs(scale - 1.0) > 1e-9:
            laser_e = [e.transformGeometry(m) for e in laser_e]

        material_kind = _material_kind_for_export(perfil)
        cyptube_objs = _build_cyptube_flatbar_iges(
            doc,
            name,
            outer_w,
            inner_w,
            plate_w,
            laser_e,
            mark_e,
            thk_mm,
            off_x,
            off_y,
            off_z,
            material_kind,
        )
        if not cyptube_objs:
            print(f"[{name}] ERROR: IGES CypTube sin objetos exportables.")
            App.closeDocument(doc.Name)
            return

        doc.recompute()
        FreeCADGui.updateGui()
        print(f"[{name}] {cad_label} destino final: {out_step}")
        try:
            test_file = out_step + ".write_test"
            with open(test_file, "wb") as tf:
                tf.write(b"ok")
            os.remove(test_file)
            print(f"[{name}] WRITE TEST OK en carpeta {cad_label}")
        except Exception as e:
            print(f"[{name}] WRITE TEST FAIL en carpeta {cad_label}: {e}")

        _configure_export_units()
        ImportGui.export(cyptube_objs, out_step)
        print(f"[{name}] {cad_label} CYPTUBE FLATBAR EXPORTADO -> {out_step}")
        print(f"==========================================================\n")
        App.closeDocument(doc.Name)
        return

    # SELECCIÓN Y CREACIÓN DEL PLATE (Cortador de Galletas)
    plate_wire = _pick_biggest_wire(plate_w)
    plate_solid = None
    try:
        if plate_wire:
            # Placa explícita: cortador de galletas clásico.
            plate_solid = _solo_solidos(
                Part.Face(plate_wire).extrude(App.Vector(0, 0, thk_mm))
            )
        elif len(outer_w) > 1:
            # Sin capa Plate (p.ej. CAMA LASER cobre): la "placa" es el COMPOUND
            # de TODAS las piezas, no solo la mayor. Con solo la mayor, el
            # intersect posterior perdía las demás piezas y se rechazaba el STEP.
            piece_solids = []
            for ow in outer_w:
                try:
                    piece_solids.append(
                        _solo_solidos(Part.Face(ow).extrude(App.Vector(0, 0, thk_mm)))
                    )
                except Exception:
                    pass
            if piece_solids:
                plate_solid = (
                    piece_solids[0]
                    if len(piece_solids) == 1
                    else Part.makeCompound(piece_solids)
                )
            plate_wire = None  # sin marco de placa: no se descarta ningún contorno
        else:
            # Una sola pieza sin Plate: usar su propio contorno como placa.
            plate_wire = _pick_biggest_wire(outer_w)
            if plate_wire:
                plate_solid = _solo_solidos(
                    Part.Face(plate_wire).extrude(App.Vector(0, 0, thk_mm))
                )
    except Exception as e:
        print(f"[{name}] ERROR construyendo PLATE: {e}")
        App.closeDocument(doc.Name)
        return

    if plate_solid is None or getattr(plate_solid, "isNull", lambda: True)():
        App.closeDocument(doc.Name)
        return

    # POSICIONAMIENTO GLOBAL
    # NONE/ASIS/KEEP: coords DXF 1:1 (solo off_*). TR/BR: ancla robot + off_*.
    caja_total = plate_solid.BoundBox
    ori_u = str(origen_tipo or "").strip().upper()
    if ori_u in ("", "NONE", "ASIS", "KEEP", "IDENTITY", "0"):
        dx_ancla, dy_ancla = 0.0, 0.0
    elif ori_u == "TR":
        dx_ancla, dy_ancla = -caja_total.XMax, -caja_total.YMax
    else:
        dx_ancla, dy_ancla = -caja_total.XMax, -caja_total.YMin

    dx_final, dy_final, dz_final = dx_ancla + off_x, dy_ancla + off_y, off_z
    mov = App.Vector(dx_final, dy_final, dz_final)

    plate_solid.translate(mov)
    outer_w_m = [w.copy().translate(mov) for w in outer_w]
    inner_w_m = [w.copy().translate(mov) for w in inner_w]
    
    mark_e_m = []
    for e in mark_e:
        try:
            ec = e.copy()
            ec.translate(App.Vector(dx_final, dy_final, 0)) # La Z se ajusta en los ribbons
            mark_e_m.append(ec)
        except: pass

    # ==========================================================
    # PASO 1: PERFORAR INNER EN EL PLATE
    # ==========================================================
    try:
        hole_tools = []
        vec_hole = App.Vector(0, 0, thk_mm + 2.0)
        for iw in inner_w_m:
            try:
                h = Part.Face(iw).extrude(vec_hole)
                h.translate(App.Vector(0, 0, -1.0))
                hole_tools.append(h)
            except: pass

        if hole_tools:
            comp_holes = Part.makeCompound(hole_tools)
            plate_solid = plate_solid.cut(comp_holes)
            plate_solid = _solo_solidos(plate_solid) # Limpiamos de inmediato
    except Exception as e:
        print(f"[{name}] ERROR cortando INNER: {e}")

    # ==========================================================
    # PASO 2: MARCAJE — placa entera (legacy) o diferido por pieza (modo C)
    # ==========================================================
    mark_mode = _normalize_mark_mode(_env_str("FREECAD_MARK_MODE", "ENGRAVE"))
    mark_z_offset = _env_float("FREECAD_MARK_Z_OFFSET", -0.5)
    rib_h = _env_float("FREECAD_MARK_RIB_H", 1.0)
    # Ancho de ranura en unidades XY del modelo (con SCALE=1 / IN ≈ 0.02").
    mark_width = _env_float("FREECAD_MARK_WIDTH", 0.02)
    vector_marcas_z = App.Vector(0, 0, dz_final + thk_mm + mark_z_offset)
    vec_up = App.Vector(0, 0, rib_h)
    per_piece_marks = _should_imprint_per_piece(len(mark_e_m))
    # ENGRAVE: siempre en pieza final para que el cookie-cut no degrade el texto.
    if mark_mode == "ENGRAVE" and mark_e_m:
        per_piece_marks = True

    if per_piece_marks:
        print(
            f"[{name}] FASE=C (sólidos->marcas por pieza) | "
            f"marcas={len(mark_e_m)} | modo={mark_mode} | ancho={mark_width}"
        )
    elif mark_e_m and _mark_mode_applies_to_solid(mark_mode):
        try:
            ribbons = _build_mark_ribbons(
                mark_e_m, vector_marcas_z, vec_up, mark_mode, width=mark_width
            )
            print(
                f"[{name}] MARK MODE = {mark_mode} | Herramientas: {len(ribbons)} "
                f"(ancho={mark_width})"
            )
            if ribbons:
                plate_solid = _apply_imprint_ribbons_on_solid(
                    plate_solid, ribbons, chunk=100, mark_mode=mark_mode
                )
        except Exception as e:
            print(f"[{name}] ERROR en proceso {mark_mode} (placa): {e}")

    # ==========================================================
    # PASO 3: EXTRACCIÓN CON EL CORTADOR DE GALLETAS (OUTER)
    # ==========================================================
    try:
        print(f"[{name}] Extrayendo piezas con INTERSECT...")
        parts = []
        vec_prism = App.Vector(0, 0, thk_mm + 2.0)
        plate_sig = _wire_signature(plate_wire) if plate_wire else None

        if not outer_w_m:
            piece = _solo_solidos(plate_solid)
            if per_piece_marks and mark_e_m and _mark_mode_applies_to_solid(mark_mode):
                piece_marks = _marks_for_piece(mark_e_m, piece.BoundBox, margin=1.5)
                ribbons = _build_mark_ribbons(
                    piece_marks, vector_marcas_z, vec_up, mark_mode, width=mark_width
                )
                piece = _apply_imprint_ribbons_on_solid(
                    piece, ribbons, chunk=50, mark_mode=mark_mode
                )
            if hasattr(piece, "Volume") and piece.Volume > 1e-6:
                parts.append(piece)
        else:
            for ow in outer_w_m:
                if plate_sig and _wire_signature(ow) == plate_sig:
                    continue
                try:
                    prism = Part.Face(ow).extrude(vec_prism)
                    prism.translate(App.Vector(0, 0, -1.0))

                    # Interceptamos el gran Plate (que ya tiene los agujeros e imprints)
                    piece = plate_solid.common(prism)

                    # Obligamos a que la pieza final no tenga basura superficial
                    piece = _solo_solidos(piece)

                    if per_piece_marks and mark_e_m and _mark_mode_applies_to_solid(mark_mode):
                        piece_marks = _marks_for_piece(mark_e_m, piece.BoundBox, margin=1.5)
                        if piece_marks:
                            ribbons = _build_mark_ribbons(
                                piece_marks,
                                vector_marcas_z,
                                vec_up,
                                mark_mode,
                                width=mark_width,
                            )
                            piece = _apply_imprint_ribbons_on_solid(
                                piece, ribbons, chunk=50, mark_mode=mark_mode
                            )

                    if hasattr(piece, "Volume") and piece.Volume > 1e-6:
                        parts.append(piece)
                except Exception:
                    pass

        if not parts:
            # Pieza única (DXF fuente) o plate = único contorno: exportar el plate ya perforado.
            piece = _solo_solidos(plate_solid)
            if per_piece_marks and mark_e_m and _mark_mode_applies_to_solid(mark_mode):
                piece_marks = _marks_for_piece(mark_e_m, piece.BoundBox, margin=1.5)
                ribbons = _build_mark_ribbons(
                    piece_marks, vector_marcas_z, vec_up, mark_mode, width=mark_width
                )
                piece = _apply_imprint_ribbons_on_solid(
                    piece, ribbons, chunk=50, mark_mode=mark_mode
                )
            if hasattr(piece, "Volume") and piece.Volume > 1e-6:
                parts.append(piece)

        if not parts:
            App.closeDocument(doc.Name)
            return

        n_outer_eff = 0
        for ow in outer_w_m:
            if plate_sig and _wire_signature(ow) == plate_sig:
                continue
            n_outer_eff += 1

        print(f"[{name}] Piezas solidas en STEP: {len(parts)} (contornos OUTER: {len(outer_w_m)}, efectivos: {n_outer_eff})")
        if n_outer_eff > 0 and len(parts) < n_outer_eff:
            print(
                f"[{name}] ERROR CRITICO: perdida de piezas en STEP "
                f"({len(parts)}/{n_outer_eff}). No se exporta STEP incompleto."
            )
            App.closeDocument(doc.Name)
            return

        # ==========================================================
        # PASO 4: EMPAQUETAR Y EXPORTAR (IPT MULTIBODY)
        # ==========================================================
        material_kind = _material_kind_for_export(perfil)
        master_compound = Part.makeCompound(parts)
        f_master = doc.addObject("Part::Feature", name)
        f_master.Shape = master_compound
        _apply_part_appearance(f_master.ViewObject, material_kind)
        print(f"[{name}] Apariencia STEP: {material_kind}")

        doc.recompute()
        FreeCADGui.updateGui()

        print(f"[{name}] {cad_label} destino final: {out_step}")
        print(f"[{name}] Carpeta {cad_label} existe: {os.path.isdir(os.path.dirname(out_step))}")
        print(f"[{name}] Carpeta {cad_label}: {os.path.dirname(out_step)}")

        try:
            test_file = out_step + ".write_test"
            with open(test_file, "wb") as tf:
                tf.write(b"ok")
            os.remove(test_file)
            print(f"[{name}] WRITE TEST OK en carpeta {cad_label}")
        except Exception as e:
            print(f"[{name}] WRITE TEST FAIL en carpeta {cad_label}: {e}")

        _configure_export_units()
        ImportGui.export([f_master], out_step)
        print(f"[{name}] {cad_label} IPT MULTIBODY EXPORTADO -> {out_step}")
        print(f"==========================================================\n")

    except Exception as e:
        print(f"[{name}] ERROR exportando: {e}")
        traceback.print_exc()

    App.closeDocument(doc.Name)

try:
    dxf_in = os.getenv("FREECAD_DXF_IN", r"C:\NEST_EXPORTS")
    step_out = os.getenv("FREECAD_STEP_OUT", dxf_in)
    thk = _env_float("FREECAD_THK_MM", 6.35)
    scl = _env_float("FREECAD_SCALE", 1.0)

    ori = os.getenv("FREECAD_ORIGIN", "TR")
    ox = _env_float("FREECAD_OFFSET_X", 0.0)
    oy = _env_float("FREECAD_OFFSET_Y", 0.0)
    oz = _env_float("FREECAD_OFFSET_Z", 0.0)

    single = os.getenv("FREECAD_DXF_SINGLE", "").strip()
    if single and os.path.isfile(single):
        files = [os.path.normpath(single)]
        print(f"Procesando 1 archivo (FREECAD_DXF_SINGLE): {files[0]}")
    else:
        files = sorted(glob.glob(os.path.join(dxf_in, "*.dxf")))
        print(f"Procesando {len(files)} archivos...")
    for f in files:
        procesar_dxf(f, step_out, thk, scl, ori, ox, oy, oz)

except Exception as e:
    print(f"ERROR GENERAL: {e}")
    traceback.print_exc()

finally:
    log_file.close()
    os._exit(0)
