Imports Inventor
Imports System.Windows.Forms
Imports System.Globalization
Imports System.IO
Imports System.Text
Imports System.Text.RegularExpressions
Imports System.Collections.Generic

'---------------------------------------------
' AutoDXF 2.0 Grupo Arga
' - Exportacion DXF por Flat Pattern
' - Orientacion automatica de cara (A-Side)
' - Normalizacion de material/espesor alineada a Arga Nesting Suite
' - Catalogo de referencia desde react-Herinox (sin logica de stock/ranking)
' - Espesor / Cal carpeta ANS:
'   * Si hay SM y empata con geometría → Cal = SM (OK).
'   * Si hay SM pero NO empata → Cal = geometría (nest correcto) + [REVISAR SM]
'     (el Thickness en Inventor está mal; hay que corregirlo por bend deduction).
'   * Si no hay SM → Cal = geometría + [REVISAR SM].
'---------------------------------------------

Public Class HerinoxCatalog
    Public Available As Boolean = False
    Public Source As String = "NONE"
    Public Message As String = ""
    Public RawMaterials As New List(Of String)
    Public CanonicalMaterials As New List(Of String)
End Class

Sub Main()

    ' 0) Verificaciones basicas
    If ThisApplication.ActiveDocument Is Nothing _
       OrElse ThisApplication.ActiveDocument.DocumentType <> DocumentTypeEnum.kAssemblyDocumentObject Then
        MessageBox.Show("Ejecuta esta regla desde un Ensamble (.iam).", "AutoDXF 2.0 Grupo Arga")
        Exit Sub
    End If

    Dim asm As AssemblyDocument = CType(ThisApplication.ActiveDocument, AssemblyDocument)
    If String.IsNullOrEmpty(asm.FullFileName) Then
        MessageBox.Show("Guarda primero el ensamble.", "AutoDXF 2.0 Grupo Arga")
        Exit Sub
    End If

    ' 1) Carpeta raiz
    Dim rootFolder As String = PickFolder("Elige carpeta destino de DXF y subcarpetas por calibre/material")
    If String.IsNullOrEmpty(rootFolder) Then Exit Sub
    Dim exportRoot As String = rootFolder
    If UCase(System.IO.Path.GetFileName(rootFolder).Trim()) <> "AUTODXF" Then
        exportRoot = System.IO.Path.Combine(rootFolder, "AutoDXF")
    End If
    If Not System.IO.Directory.Exists(exportRoot) Then
        System.IO.Directory.CreateDirectory(exportRoot)
    End If

    ' 1.1) Bootstrap automático: ejecuta puente Python para preparar herinox_sync.local.json
    Dim bridgeLog As String = ""
    Try
        Dim asmDir As String = ""
        Try
            asmDir = System.IO.Path.GetDirectoryName(asm.FullFileName)
        Catch
            asmDir = ""
        End Try
        EnsureHerinoxJsonViaPython(asmDir, bridgeLog)
    Catch ex As Exception
        bridgeLog = "Bridge Python error: " & ex.Message
    End Try

    ' 2) Catalogo Herinox (solo normalizacion de nomenclatura)
    Dim catalog As HerinoxCatalog = TryLoadHerinoxCatalog()

    ' 3) BOM Parts Only
    Dim BOM As BOM = asm.ComponentDefinition.BOM
    BOM.PartsOnlyViewEnabled = True
    Dim BOMView As BOMView = BOM.BOMViews.Item(BOM.BOMViews.Count)

    Dim exported As Integer = 0
    Dim sb As New System.Text.StringBuilder()
    Dim nombreAsm As String = System.IO.Path.GetFileNameWithoutExtension(asm.FullFileName)
    Dim csvDxfPath As String = System.IO.Path.Combine(exportRoot,
        "CLASIFICACION_DXF_" & nombreAsm & "_" & DateTime.Now.ToString("yyyyMMdd_HHmmss") & ".csv")
    Dim csvDxf As System.IO.StreamWriter = Nothing
    Try
        csvDxf = New System.IO.StreamWriter(csvDxfPath, False, Encoding.UTF8)
        csvDxf.WriteLine("NombreComponente;Clasificacion")
    Catch ex As Exception
        sb.AppendLine("No se pudo crear CSV de clasificación DXF: " & ex.Message)
        csvDxf = Nothing
    End Try

    ' 3.1) CSV completo: todas las piezas del ensamble (incluye Almacén, sólidos, gaskets, etc.)
    Dim csvPartCount As Integer = 0
    If csvDxf IsNot Nothing Then
        csvPartCount = WriteCsvClasificacionCompleto(asm, csvDxf, sb)
    End If

    sb.AppendLine("Herinox Catalogo: " & If(catalog.Available, "OK (" & catalog.Source & ")", "FALLBACK"))
    If Not String.IsNullOrEmpty(catalog.Message) Then
        sb.AppendLine("Detalle catalogo: " & catalog.Message)
    End If
    If Not String.IsNullOrEmpty(bridgeLog) Then
        sb.AppendLine("Bridge Python: " & bridgeLog)
    End If

    ' 4) Recorremos filas
    For Each Row As BOMRow In BOMView.BOMRows
        Try
            Dim def As ComponentDefinition = Row.ComponentDefinitions(1)
            If Not TypeOf def Is SheetMetalComponentDefinition Then Continue For

            Dim smDef As SheetMetalComponentDefinition = CType(def, SheetMetalComponentDefinition)
            Dim part As PartDocument = CType(smDef.Document, PartDocument)

            If String.IsNullOrEmpty(part.FullFileName) Then
                sb.AppendLine("No guardado: " & part.DisplayName)
                Continue For
            End If

            ' 4.0) Verificar si el archivo ya estaba abierto
            Dim wasOpen As Boolean = False
            For Each doc As Document In ThisApplication.Documents
                If doc.FullFileName = part.FullFileName Then
                    wasOpen = True
                    Exit For
                End If
            Next

            If Not wasOpen Then
                part = ThisApplication.Documents.Open(part.FullFileName, True)
            End If

            ' 4.1) Flat Pattern: intentar sanear (aviso si falla).
            Dim flatOk As Boolean = EnsureFlatPatternHealthy(smDef)
            Dim marcarRevisarSm As Boolean = False
            If Not flatOk Then
                sb.AppendLine( _
                    "AVISO (Flat Pattern): " & part.DisplayName & _
                    " — Flat dudoso; revisar en Inventor.")
                Try
                    EnsureFlatPattern(smDef)
                Catch
                End Try
            End If

            ' 4.2) Seleccion automatica de cara plana para A-Side
            Try
                Dim topFace As Face = GetLargestPlanarFace(part)
                If Not topFace Is Nothing Then
                    TrySetTopFace(smDef, topFace)
                Else
                    sb.AppendLine("No se encontro cara plana para: " & part.DisplayName)
                End If
            Catch ex As Exception
                sb.AppendLine("Error al definir cara A-Side en: " & part.DisplayName & " - " & ex.Message)
            End Try

            ' 4.3) Cal para ANS: SM si empata; si SM≠pieza → geo + [REVISAR SM].
            Dim invMaterial As String = SafeMaterialName(smDef, part)
            Dim materialName As String = NormalizeMaterialForArga(invMaterial, catalog)
            Dim thkTxt As String = "0"
            Dim thkWarn As String = ""
            Try
                Dim thkNote As String = ""
                Dim thkIn As Double = ResolvePartThicknessInches(smDef, part, thkNote, thkWarn, marcarRevisarSm)
                thkTxt = FormatThicknessForArga(thkIn, materialName)
                If Not String.IsNullOrWhiteSpace(thkNote) Then
                    sb.AppendLine("Espesor " & part.DisplayName & ": " & thkNote & " → Cal " & thkTxt)
                End If
                If Not String.IsNullOrWhiteSpace(thkWarn) Then
                    sb.AppendLine("AVISO espesor " & part.DisplayName & ": " & thkWarn)
                End If
            Catch exThk As Exception
                marcarRevisarSm = True
                sb.AppendLine("Espesor fallback en " & part.DisplayName & ": " & exThk.Message)
                thkTxt = "0"
            End Try
            If String.IsNullOrWhiteSpace(thkTxt) OrElse thkTxt = "0" Then
                marcarRevisarSm = True
                thkTxt = "0"
                sb.AppendLine("AVISO: " & part.DisplayName & " — espesor 0; carpeta [REVISAR SM].")
            End If

            ' 4.5) Cantidad
            Dim qty As Integer = CInt(Math.Round(Row.ItemQuantity, 0))

            ' 4.6) [REVISAR SM] = Thickness SM mal/ausente (Cal ya va por medida real si se pudo).
            Dim subFolder As String = "Cal " & thkTxt & " " & materialName
            If marcarRevisarSm Then
                subFolder = subFolder & " [REVISAR SM]"
            End If
            Dim targetFolder As String = System.IO.Path.Combine(exportRoot, SanitizeForPath(subFolder))
            If Not Directory.Exists(targetFolder) Then
                Directory.CreateDirectory(targetFolder)
            End If

            ' 4.7) Nombre archivo canonico
            Dim baseName As String = System.IO.Path.GetFileNameWithoutExtension(part.DisplayName)
            Dim fileName As String = baseName & ", " & materialName & ", QTY " & qty.ToString() _
                                   & ", Cal " & thkTxt & ".dxf"
            If marcarRevisarSm Then
                fileName = baseName & ", " & materialName & ", QTY " & qty.ToString() _
                         & ", Cal " & thkTxt & ", REVISAR SM.dxf"
            End If
            Dim outPath As String = System.IO.Path.Combine(targetFolder, SanitizeForFileName(fileName))

            ' 4.8) Exportar DXF (el flat de Inventor sigue usando el SM del IPT).
            Try
                ExportFlatPatternDXF(part, outPath)
                exported += 1
                If marcarRevisarSm Then
                    sb.AppendLine("Exportado [REVISAR SM]: " & part.DisplayName & " → " & subFolder & _
                                  " (corrige Sheet Metal Thickness en Inventor).")
                End If
            Catch exExp As Exception
                sb.AppendLine( _
                    "AVISO export DXF " & part.DisplayName & ": " & exExp.Message & _
                    " — revisar Sheet Metal / Flat Pattern en Inventor.")
            End Try

            ' 4.9) Cerrar documento si fue abierto por esta rutina
            If Not wasOpen Then
                part.Close(True)
            End If

        Catch ex As System.Exception
            sb.AppendLine("Error en fila BOM: " & ex.Message)
        End Try
    Next

    If csvDxf IsNot Nothing Then
        Try
            csvDxf.Flush()
            csvDxf.Close()
        Catch
        End Try
        csvDxf = Nothing
    End If

    ' 5) Mensaje final
    Dim msg As String = "DXF exportados: " & exported.ToString() & vbCrLf
    If System.IO.File.Exists(csvDxfPath) Then
        msg &= "Piezas en CSV (todo el ensamble): " & csvPartCount.ToString() & vbCrLf
        msg &= "CSV clasificación:" & vbCrLf & csvDxfPath & vbCrLf
    End If
    If sb.Length > 0 Then
        msg &= vbCrLf & "Omisiones/avisos:" & vbCrLf & sb.ToString()
    End If
    MessageBox.Show(msg, "AutoDXF 2.0 Grupo Arga")
End Sub

Private Function WriteCsvClasificacionCompleto(asm As AssemblyDocument, csv As StreamWriter, sb As StringBuilder) As Integer
    Dim partMap As New Dictionary(Of String, Boolean)(StringComparer.OrdinalIgnoreCase)
    Dim allOccs As New List(Of ComponentOccurrence)
    Dim count As Integer = 0

    CollectAllPartOccurrences(asm.ComponentDefinition.Occurrences, allOccs)

    For Each occ As ComponentOccurrence In allOccs
        Try
            Dim doc As Document = occ.Definition.Document
            If Not TypeOf doc Is PartDocument Then Continue For

            Dim part As PartDocument = CType(doc, PartDocument)
            Dim key As String = ""
            Try
                key = part.FullFileName
            Catch
            End Try
            If String.IsNullOrEmpty(key) Then key = part.DisplayName
            If partMap.ContainsKey(key) Then Continue For
            partMap(key) = True

            Dim nombre As String = System.IO.Path.GetFileNameWithoutExtension(part.DisplayName)
            Dim clasificacion As String = GetClasificacionPieza(part)
            csv.WriteLine(CsvSafeDxf(nombre) & ";" & CsvSafeDxf(clasificacion))
            count += 1
        Catch ex As Exception
            sb.AppendLine("CSV omitido para ocurrencia: " & ex.Message)
        End Try
    Next

    csv.Flush()
    Return count
End Function

Private Sub CollectAllPartOccurrences(occs As ComponentOccurrences, list As List(Of ComponentOccurrence))
    For Each o As ComponentOccurrence In occs
        If o.Suppressed Then Continue For
        list.Add(o)
        Try
            If o.SubOccurrences IsNot Nothing AndAlso o.SubOccurrences.Count > 0 Then
                CollectAllPartOccurrences(o.SubOccurrences, list)
            End If
        Catch
        End Try
    Next
End Sub

Private Function GetClasificacionPieza(part As PartDocument) As String
    Try
        Dim customProps As PropertySet = part.PropertySets.Item("Inventor User Defined Properties")
        Dim prop As [Property] = customProps.Item("Clasificación")
        If prop.Value IsNot Nothing Then
            Return prop.Value.ToString().Trim()
        End If
    Catch
    End Try
    Return ""
End Function

Private Function CsvSafeDxf(value As String) As String
    If String.IsNullOrEmpty(value) Then Return ""
    Return value.Replace(";", ",").Replace(vbCr, " ").Replace(vbLf, " ")
End Function

'------------------------------ HERINOX ------------------------------

Private Function TryLoadHerinoxCatalog() As HerinoxCatalog
    Dim cat As New HerinoxCatalog()
    Try
        Dim cfg As Dictionary(Of String, String) = ReadHerinoxConfig()
        Dim rawCsv As String = GetCfg(cfg, "raw_materials_csv", "")
        Dim canonicalCsv As String = GetCfg(cfg, "canonical_materials_csv", "")
        Dim cfgPath As String = GetCfg(cfg, "__config_path", "")
        Dim lookupPaths As String = GetCfg(cfg, "__lookup_paths", "")
        Dim autoCreated As String = GetCfg(cfg, "__auto_created", "")
        Dim autoCreateErr As String = GetCfg(cfg, "__auto_create_error", "")
        Dim bridgeSource As String = GetCfg(cfg, "bridge_source", "")
        Dim bridgeDetail As String = GetCfg(cfg, "bridge_detail", "")

        Dim rawMats As New HashSet(Of String)(StringComparer.OrdinalIgnoreCase)
        If Not String.IsNullOrEmpty(rawCsv) Then
            For Each rawPart In rawCsv.Split("|"c)
                Dim mRaw As String = Trim(rawPart)
                If mRaw <> "" Then rawMats.Add(mRaw)
            Next
        End If

        Dim bridgeMats As New HashSet(Of String)(StringComparer.OrdinalIgnoreCase)
        If Not String.IsNullOrEmpty(canonicalCsv) Then
            For Each rawPart In canonicalCsv.Split("|"c)
                Dim m As String = NormalizeMaterialAlias(rawPart)
                If m <> "" Then bridgeMats.Add(m)
            Next
        End If

        ' Si no viene lista canónica, la derivamos de la lista cruda real de Herinox.
        If bridgeMats.Count = 0 AndAlso rawMats.Count > 0 Then
            For Each rawName In rawMats
                Dim nm As String = NormalizeMaterialAlias(rawName)
                If nm <> "" Then bridgeMats.Add(nm)
            Next
        End If

        If bridgeMats.Count > 0 OrElse rawMats.Count > 0 Then
            cat.Available = True
            cat.Source = "PY_BRIDGE"
            cat.RawMaterials = New List(Of String)
            For Each m In rawMats
                cat.RawMaterials.Add(m)
            Next
            cat.CanonicalMaterials = New List(Of String)
            For Each m In bridgeMats
                cat.CanonicalMaterials.Add(m)
            Next
            cat.Message = "Catalogo cargado desde herinox_sync.local.json (puente Python)." & vbCrLf & _
                          "Archivo: " & If(cfgPath <> "", cfgPath, "[NO ENCONTRADO]") & vbCrLf & _
                          If(bridgeSource <> "", "Bridge source: " & bridgeSource & vbCrLf, "") & _
                          If(bridgeDetail <> "", "Bridge detail: " & bridgeDetail & vbCrLf, "") & _
                          "Materiales crudos (DB): " & cat.RawMaterials.Count.ToString() & vbCrLf & _
                          "Materiales canonicos detectados: " & cat.CanonicalMaterials.Count.ToString()
            Return cat
        End If

        cat.Available = False
        cat.Source = "FALLBACK"
        cat.Message = "No se pudo cargar catalogo desde herinox_sync.local.json (puente Python)." & vbCrLf & _
                      "Archivo usado: " & If(cfgPath <> "", cfgPath, "[NO ENCONTRADO]") & vbCrLf & _
                      "Rutas buscadas: " & If(lookupPaths <> "", lookupPaths, "[SIN RUTAS]") & vbCrLf & _
                      If(autoCreated = "true", "Se creo automaticamente el archivo de configuracion." & vbCrLf, "") & _
                      If(autoCreateErr <> "", "Error creando config: " & autoCreateErr & vbCrLf, "") & _
                      If(bridgeSource <> "", "Bridge source: " & bridgeSource & vbCrLf, "") & _
                      If(bridgeDetail <> "", "Bridge detail: " & bridgeDetail & vbCrLf, "") & _
                      "Se usa normalizacion local."
        Return cat

    Catch ex As Exception
        cat.Available = False
        cat.Source = "FALLBACK"
        cat.Message = "No se pudo leer catalogo del puente Python: " & ex.Message & vbCrLf & _
                      "Se usa normalizacion local."
        Return cat
    End Try
End Function

Private Sub EnsureHerinoxJsonViaPython(asmDir As String, ByRef logMsg As String)
    logMsg = ""
    Dim ruleDir As String = ResolveRuleBaseDir(asmDir)
    If String.IsNullOrEmpty(ruleDir) Then
        logMsg = "No se pudo resolver carpeta para puente Python."
        Exit Sub
    End If

    Dim pyScript As String = FindBridgeScript(ruleDir, asmDir)
    If Not System.IO.File.Exists(pyScript) Then
        logMsg = "No existe Consulta_Herinox.py (ni alias) en rutas esperadas. Base: " & ruleDir
        Exit Sub
    End If

    Dim pyDir As String = System.IO.Path.GetDirectoryName(pyScript)
    Dim targetJson As String = System.IO.Path.Combine(pyDir, "herinox_sync.local.json")
    Dim pyExeCandidates As New List(Of String)
    pyExeCandidates.Add("C:\Users\jose_rosales\AppData\Local\Programs\Python\Python314\python.exe")
    pyExeCandidates.Add("python")
    pyExeCandidates.Add("py")

    Dim shell As Object = CreateObject("WScript.Shell")
    For Each pyExeRaw In pyExeCandidates
        Try
            Dim pyExe As String = CStr(pyExeRaw)
            Dim cmd As String = ""
            If LCase(pyExe) = "py" Then
                cmd = """" & pyExe & """ -3 """ & pyScript & """ """ & targetJson & """"
            Else
                cmd = """" & pyExe & """ """ & pyScript & """ """ & targetJson & """"
            End If

            Dim proc As Object = shell.Exec(cmd)
            Do While proc.Status = 0
                System.Threading.Thread.Sleep(120)
            Loop
            Dim rc As Integer = CInt(proc.ExitCode)
            Dim stdOut As String = ""
            Dim stdErr As String = ""
            Try
                stdOut = CStr(proc.StdOut.ReadAll())
            Catch
                stdOut = ""
            End Try
            Try
                stdErr = CStr(proc.StdErr.ReadAll())
            Catch
                stdErr = ""
            End Try
            If rc = 0 Then
                logMsg = "OK (" & pyExe & ") -> " & targetJson
                If Not String.IsNullOrEmpty(stdOut) Then
                    Dim out1 As String = stdOut.Replace(vbCr, " ").Replace(vbLf, " ").Trim()
                    If out1.Length > 220 Then out1 = out1.Substring(0, 220) & "..."
                    logMsg &= " | " & out1
                End If
                Exit Sub
            End If
            Dim detail As String = (stdErr & " " & stdOut).Replace(vbCr, " ").Replace(vbLf, " ").Trim()
            If detail.Length > 240 Then detail = detail.Substring(0, 240) & "..."
            logMsg = "ExitCode " & rc.ToString() & " con " & pyExe & If(detail <> "", " | " & detail, "")
        Catch ex As Exception
            logMsg = ex.Message
        End Try
    Next
End Sub

Private Function FindBridgeScript(ruleDir As String, asmDir As String) As String
    Dim names As New List(Of String)
    names.Add("Consulta_Herinox.py")
    names.Add("Consuta_Herinox.py")
    names.Add("Consuta_Herino.py")

    Dim dirs As New List(Of String)
    If Not String.IsNullOrEmpty(ruleDir) Then
        dirs.Add(ruleDir)
        dirs.Add(System.IO.Path.Combine(ruleDir, "AutoDXF 2.0"))
    End If
    If Not String.IsNullOrEmpty(asmDir) Then
        If Not dirs.Contains(asmDir) Then dirs.Add(asmDir)
        dirs.Add(System.IO.Path.Combine(asmDir, "AutoDXF 2.0"))
    End If

    For Each d In dirs
        Try
            If String.IsNullOrEmpty(d) OrElse Not System.IO.Directory.Exists(d) Then Continue For
            For Each n In names
                Dim p As String = System.IO.Path.Combine(d, n)
                If System.IO.File.Exists(p) Then
                    Return p
                End If
            Next
        Catch
        End Try
    Next

    ' Búsqueda recursiva corta en base ruleDir/asmDir por nombre esperado.
    Dim bases As New List(Of String)
    If Not String.IsNullOrEmpty(ruleDir) Then bases.Add(ruleDir)
    If Not String.IsNullOrEmpty(asmDir) AndAlso Not bases.Contains(asmDir) Then bases.Add(asmDir)
    For Each b In bases
        Try
            If Not System.IO.Directory.Exists(b) Then Continue For
            Dim files() As String = System.IO.Directory.GetFiles(b, "*.py", System.IO.SearchOption.AllDirectories)
            For Each f In files
                Dim fn As String = UCase(System.IO.Path.GetFileName(f))
                If fn = "CONSULTA_HERINOX.PY" OrElse fn = "CONSUTA_HERINOX.PY" OrElse fn = "CONSUTA_HERINO.PY" Then
                    Return f
                End If
            Next
        Catch
        End Try
    Next
    Return ""
End Function

Private Function ResolveRuleBaseDir(asmDir As String) As String
    Dim candidates As New List(Of String)
    Try
        Dim p As String = ""
        p = System.IO.Path.GetDirectoryName(ThisDoc.Path)
        If Not String.IsNullOrEmpty(p) Then candidates.Add(p)
    Catch
    End Try
    If Not String.IsNullOrEmpty(asmDir) Then candidates.Add(asmDir)
    Try
        Dim p2 As String = System.Environment.CurrentDirectory
        If Not String.IsNullOrEmpty(p2) AndAlso Not candidates.Contains(p2) Then candidates.Add(p2)
    Catch
    End Try

    ' 1) Si ya existe la regla en el candidato, usamos ese directorio.
    For Each d In candidates
        Try
            If String.IsNullOrEmpty(d) OrElse Not System.IO.Directory.Exists(d) Then Continue For
            Dim r1 As String = System.IO.Path.Combine(d, "AutoDXF 2.0.iLogicVb")
            Dim r2 As String = System.IO.Path.Combine(d, "AutoDXF.iLogicVb")
            If System.IO.File.Exists(r1) OrElse System.IO.File.Exists(r2) Then Return d
        Catch
        End Try
    Next

    ' 2) Buscamos la regla en ubicaciones típicas (Desktop/OneDrive) y usamos su carpeta.
    Dim roots As New List(Of String)
    Try
        Dim desktop As String = System.Environment.GetFolderPath(System.Environment.SpecialFolder.DesktopDirectory)
        If Not String.IsNullOrEmpty(desktop) Then roots.Add(desktop)
    Catch
    End Try
    Try
        Dim oneDrive As String = System.Environment.GetEnvironmentVariable("OneDrive")
        If Not String.IsNullOrEmpty(oneDrive) Then
            Dim odDesk As String = System.IO.Path.Combine(oneDrive, "Desktop")
            If System.IO.Directory.Exists(odDesk) Then roots.Add(odDesk)
        End If
    Catch
    End Try
    Try
        Dim oneDriveBiz As String = System.Environment.GetEnvironmentVariable("OneDriveCommercial")
        If Not String.IsNullOrEmpty(oneDriveBiz) Then
            Dim odbDesk As String = System.IO.Path.Combine(oneDriveBiz, "Desktop")
            If System.IO.Directory.Exists(odbDesk) Then roots.Add(odbDesk)
        End If
    Catch
    End Try
    If Not String.IsNullOrEmpty(asmDir) Then
        Try
            Dim p As String = asmDir
            Dim i As Integer = 0
            While (Not String.IsNullOrEmpty(p)) AndAlso (i < 4)
                If Not roots.Contains(p) Then roots.Add(p)
                Dim parent As String = System.IO.Path.GetDirectoryName(p)
                If String.Equals(parent, p, StringComparison.OrdinalIgnoreCase) Then Exit While
                p = parent
                i += 1
            End While
        Catch
        End Try
    End If

    For Each root In roots
        Dim foundRule As String = TryFindFileRecursive(root, "AutoDXF 2.0.iLogicVb", 5)
        If String.IsNullOrEmpty(foundRule) Then
            foundRule = TryFindFileRecursive(root, "AutoDXF.iLogicVb", 5)
        End If
        If Not String.IsNullOrEmpty(foundRule) Then
            Try
                Dim dirRule As String = System.IO.Path.GetDirectoryName(foundRule)
                If Not String.IsNullOrEmpty(dirRule) Then Return dirRule
            Catch
            End Try
        End If
    Next

    ' 3) Último fallback a carpeta de ensamble.
    Return asmDir
End Function

Private Function TryFindFileRecursive(root As String, fileName As String, maxDepth As Integer) As String
    If String.IsNullOrEmpty(root) Then Return ""
    If Not System.IO.Directory.Exists(root) Then Return ""
    Try
        Dim direct As String = System.IO.Path.Combine(root, fileName)
        If System.IO.File.Exists(direct) Then Return direct
    Catch
    End Try
    If maxDepth <= 0 Then Return ""

    Try
        Dim files() As String = System.IO.Directory.GetFiles(root, fileName, SearchOption.TopDirectoryOnly)
        If files IsNot Nothing AndAlso files.Length > 0 Then
            Return files(0)
        End If
    Catch
    End Try

    Dim subs() As String = Nothing
    Try
        subs = System.IO.Directory.GetDirectories(root, "*", SearchOption.TopDirectoryOnly)
    Catch
        subs = Nothing
    End Try
    If subs Is Nothing Then Return ""

    For Each d In subs
        Dim found As String = TryFindFileRecursive(d, fileName, maxDepth - 1)
        If Not String.IsNullOrEmpty(found) Then Return found
    Next
    Return ""
End Function

Private Function HerinoxLogin(baseUrl As String, email As String, password As String, timeoutSec As Integer) As String
    Dim url As String = baseUrl & "/api/auth/login"
    Dim payload As String = "{""email"":""" & JsonEscape(email) & """,""password"":""" & JsonEscape(password) & """}"
    Dim raw As String = HttpJsonRequest(url, "POST", payload, "", timeoutSec)
    Dim token As String = JsonGetString(raw, "token")
    If String.IsNullOrEmpty(token) Then
        Throw New Exception("Login sin token.")
    End If
    Return token
End Function

Private Function HerinoxFetchPlateMaterials(baseUrl As String, token As String, timeoutSec As Integer) As List(Of String)
    Dim url As String = baseUrl & "/api/plates"
    Dim raw As String = HttpJsonRequest(url, "GET", "", token, timeoutSec)
    Dim out As New List(Of String)
    If String.IsNullOrEmpty(raw) Then Return out

    Dim rx As New Regex("""material""\s*:\s*""(?<m>[^""]*)""", RegexOptions.IgnoreCase)
    Dim seen As New HashSet(Of String)(StringComparer.OrdinalIgnoreCase)
    For Each mt As Match In rx.Matches(raw)
        Dim m As String = mt.Groups("m").Value.Trim()
        If m <> "" AndAlso Not seen.Contains(m) Then
            seen.Add(m)
            out.Add(m)
        End If
    Next
    Return out
End Function

Private Function TryLoadMaterialCatalogFromDb(host As String, port As String, dbName As String, userName As String, password As String, ByRef errMsg As String) As List(Of String)
    Dim matsNpgsql As List(Of String) = TryLoadMaterialCatalogFromDbWithNpgsql(host, port, dbName, userName, password, errMsg)
    If matsNpgsql IsNot Nothing AndAlso matsNpgsql.Count > 0 Then
        Return matsNpgsql
    End If

    Dim materials As New List(Of String)
    Dim conn As Object = Nothing
    Dim rs As Object = Nothing
    If String.IsNullOrEmpty(errMsg) Then errMsg = ""

    Dim connCandidates As New List(Of String)
    ' OLE DB directos (si existen en la estación)
    connCandidates.Add("Provider=PostgreSQL OLE DB Provider;Data Source=" & host & ";Location=" & dbName & ";User ID=" & userName & ";Password=" & password & ";Port=" & port & ";")
    connCandidates.Add("Provider=PostgreSQL.1;Data Source=" & host & ";Location=" & dbName & ";User ID=" & userName & ";Password=" & password & ";Port=" & port & ";")
    ' ODBC DSN-less
    connCandidates.Add("Driver={PostgreSQL Unicode(x64)};Server=" & host & ";Port=" & port & ";Database=" & dbName & ";Uid=" & userName & ";Pwd=" & password & ";")
    connCandidates.Add("Driver={PostgreSQL Unicode};Server=" & host & ";Port=" & port & ";Database=" & dbName & ";Uid=" & userName & ";Pwd=" & password & ";")
    connCandidates.Add("Driver={PostgreSQL ANSI(x64)};Server=" & host & ";Port=" & port & ";Database=" & dbName & ";Uid=" & userName & ";Pwd=" & password & ";")
    connCandidates.Add("Driver={PostgreSQL ANSI};Server=" & host & ";Port=" & port & ";Database=" & dbName & ";Uid=" & userName & ";Pwd=" & password & ";")

    Dim sql As String = _
        "SELECT DISTINCT p.""material"" " & _
        "FROM ""Plate"" p " & _
        "WHERE p.""material"" IS NOT NULL " & _
        "  AND TRIM(p.""material"") <> '' " & _
        "  AND p.""codigo"" IS NOT NULL " & _
        "  AND TRIM(p.""codigo"") <> '' " & _
        "  AND COALESCE(p.""inventoryType"", 'PLATE') IN ('PLATE','PLACA','LAMINA');"

    For Each cs In connCandidates
        Try
            conn = CreateObject("ADODB.Connection")
            conn.CommandTimeout = 6
            conn.ConnectionTimeout = 6
            conn.Open(cs)

            rs = CreateObject("ADODB.Recordset")
            rs.Open(sql, conn)
            Do While Not rs.EOF
                Dim v As String = ""
                Try
                    v = CStr(rs.Fields(0).Value).Trim()
                Catch
                    v = ""
                End Try
                If v <> "" AndAlso Not materials.Contains(v) Then
                    materials.Add(v)
                End If
                rs.MoveNext()
            Loop
            rs.Close()
            conn.Close()
            Return materials
        Catch ex As Exception
            Try
                If rs IsNot Nothing Then rs.Close()
            Catch
            End Try
            Try
                If conn IsNot Nothing Then conn.Close()
            Catch
            End Try
            errMsg = ex.Message
            ' intenta siguiente driver
        End Try
    Next

    If errMsg = "" Then
        errMsg = "No se encontro un driver ODBC/OLE DB PostgreSQL compatible o no hubo respuesta del servidor."
    End If
    Return New List(Of String)()
End Function

Private Function TryLoadMaterialCatalogFromDbWithNpgsql(host As String, port As String, dbName As String, userName As String, password As String, ByRef errMsg As String) As List(Of String)
    Dim out As New List(Of String)
    Try
        Dim tConn As Type = Type.GetType("Npgsql.NpgsqlConnection, Npgsql", False)
        Dim tCmd As Type = Type.GetType("Npgsql.NpgsqlCommand, Npgsql", False)
        If tConn Is Nothing OrElse tCmd Is Nothing Then
            Return out
        End If

        Dim connStr As String = "Host=" & host & ";Port=" & port & ";Database=" & dbName & ";Username=" & userName & ";Password=" & password & ";Timeout=6;Command Timeout=6;"
        Dim conn As Object = Activator.CreateInstance(tConn, New Object() {connStr})
        conn.Open()

        Dim sql As String = _
            "SELECT DISTINCT p.""material"" " & _
            "FROM ""Plate"" p " & _
            "WHERE p.""material"" IS NOT NULL " & _
            "  AND TRIM(p.""material"") <> '' " & _
            "  AND p.""codigo"" IS NOT NULL " & _
            "  AND TRIM(p.""codigo"") <> '' " & _
            "  AND COALESCE(p.""inventoryType"", 'PLATE') IN ('PLATE','PLACA','LAMINA');"

        Dim cmd As Object = Activator.CreateInstance(tCmd, New Object() {sql, conn})
        Dim rdr As Object = cmd.ExecuteReader()
        Dim seen As New HashSet(Of String)(StringComparer.OrdinalIgnoreCase)
        Do While rdr.Read()
            Dim m As String = ""
            Try
                m = CStr(rdr.GetValue(0)).Trim()
            Catch
                m = ""
            End Try
            If m <> "" AndAlso Not seen.Contains(m) Then
                seen.Add(m)
                out.Add(m)
            End If
        Loop
        Try
            rdr.Close()
        Catch
        End Try
        Try
            conn.Close()
        Catch
        End Try
        Return out
    Catch ex As Exception
        errMsg = "Npgsql: " & ex.Message
        Return New List(Of String)()
    End Try
End Function

Private Function HttpJsonRequest(url As String, method As String, body As String, token As String, timeoutSec As Integer) As String
    Dim xhr As Object = Nothing
    Try
        xhr = CreateObject("MSXML2.ServerXMLHTTP.6.0")
    Catch
        xhr = CreateObject("MSXML2.XMLHTTP")
    End Try

    If xhr Is Nothing Then
        Throw New Exception("No se pudo crear cliente HTTP COM.")
    End If

    Dim m As String = UCase(Trim(method))
    xhr.Open(m, url, False)
    Try
        xhr.setTimeouts(timeoutSec * 1000, timeoutSec * 1000, timeoutSec * 1000, timeoutSec * 1000)
    Catch
        ' Algunos proveedores COM no exponen setTimeouts; se ignora sin romper.
    End Try
    xhr.setRequestHeader("Content-Type", "application/json")
    If Not String.IsNullOrEmpty(token) Then
        xhr.setRequestHeader("Authorization", "Bearer " & token)
    End If

    If m = "POST" Then
        xhr.send(body)
    Else
        xhr.send()
    End If

    Dim statusCode As Integer = 0
    Try
        statusCode = CInt(xhr.status)
    Catch
        statusCode = 0
    End Try
    Dim respText As String = ""
    Try
        respText = CStr(xhr.responseText)
    Catch
        respText = ""
    End Try

    If statusCode < 200 OrElse statusCode >= 300 Then
        Throw New Exception("HTTP " & statusCode.ToString() & ": " & respText)
    End If
    Return respText
End Function

Private Function ReadHerinoxConfig() As Dictionary(Of String, String)
    Dim out As New Dictionary(Of String, String)(StringComparer.OrdinalIgnoreCase)

    ' Busca config junto a esta regla y en carpeta del ensamble.
    Dim asmDir As String = ""
    Try
        asmDir = System.IO.Path.GetDirectoryName(ThisDoc.Document.FullFileName)
    Catch
        asmDir = ""
    End Try
    Dim thisRuleDir As String = ResolveRuleBaseDir(asmDir)

    Dim candidates As New List(Of String)
    If Not String.IsNullOrEmpty(thisRuleDir) Then candidates.Add(System.IO.Path.Combine(thisRuleDir, "herinox_sync.local.json"))
    If Not String.IsNullOrEmpty(asmDir) Then candidates.Add(System.IO.Path.Combine(asmDir, "herinox_sync.local.json"))
    out("__lookup_paths") = String.Join(" | ", candidates.ToArray())

    Dim cfgPath As String = ""
    For Each p In candidates
        If System.IO.File.Exists(p) Then
            cfgPath = p
            Exit For
        End If
    Next

    If String.IsNullOrEmpty(cfgPath) Then
        Dim createAt As String = ""
        If Not String.IsNullOrEmpty(thisRuleDir) Then
            createAt = System.IO.Path.Combine(thisRuleDir, "herinox_sync.local.json")
        ElseIf Not String.IsNullOrEmpty(asmDir) Then
            createAt = System.IO.Path.Combine(asmDir, "herinox_sync.local.json")
        End If

        If Not String.IsNullOrEmpty(createAt) Then
            Try
                Dim parentDir As String = System.IO.Path.GetDirectoryName(createAt)
                If Not String.IsNullOrEmpty(parentDir) AndAlso Not System.IO.Directory.Exists(parentDir) Then
                    System.IO.Directory.CreateDirectory(parentDir)
                End If
                If Not System.IO.File.Exists(createAt) Then
                    System.IO.File.WriteAllText(createAt, BuildHerinoxConfigTemplate(), Encoding.UTF8)
                    out("__auto_created") = "true"
                End If
                out("__config_path") = createAt
            Catch ex As Exception
                out("__config_path") = ""
                out("__auto_create_error") = ex.Message
            End Try
        Else
            out("__config_path") = ""
        End If
        Return out
    End If
    out("__config_path") = cfgPath

    Dim raw As String = System.IO.File.ReadAllText(cfgPath)
    out("raw_materials_csv") = JsonGetString(raw, "raw_materials_csv")
    out("canonical_materials_csv") = JsonGetString(raw, "canonical_materials_csv")
    out("raw_materials_count") = JsonGetString(raw, "raw_materials_count")
    out("canonical_materials_count") = JsonGetString(raw, "canonical_materials_count")
    out("bridge_source") = JsonGetString(raw, "bridge_source")
    out("bridge_detail") = JsonGetString(raw, "bridge_detail")
    out("bridge_updated_at") = JsonGetString(raw, "bridge_updated_at")
    out("enabled") = JsonGetString(raw, "enabled")
    out("api_base_url") = JsonGetString(raw, "api_base_url")
    out("email") = JsonGetString(raw, "email")
    out("password") = JsonGetString(raw, "password")
    out("timeout_seconds") = JsonGetString(raw, "timeout_seconds")
    out("db_host") = JsonGetString(raw, "db_host")
    out("db_port") = JsonGetString(raw, "db_port")
    out("db_name") = JsonGetString(raw, "db_name")
    out("db_user") = JsonGetString(raw, "db_user")
    out("db_password") = JsonGetString(raw, "db_password")
    Return out
End Function

Private Function BuildHerinoxConfigTemplate() As String
    Dim sb As New StringBuilder()
    sb.AppendLine("{")
    sb.AppendLine("  ""enabled"": true,")
    sb.AppendLine("  ""raw_materials_csv"": ""A 36|A 36 GALV|SSTL 304|Aluminio"",")
    sb.AppendLine("  ""canonical_materials_csv"": ""A 36|A 36 GALV|SSTL 304|Aluminio"",")
    sb.AppendLine("  ""raw_materials_count"": 4,")
    sb.AppendLine("  ""canonical_materials_count"": 4,")
    sb.AppendLine("  ""bridge_source"": ""TEMPLATE"",")
    sb.AppendLine("  ""bridge_detail"": ""Template local; se recomienda ejecutar Consulta_Herinox.py"",")
    sb.AppendLine("  ""_nota"": ""Auto-creado por AutoDXF 2.0 para consumo de catalogo canonico.""")
    sb.AppendLine("}")
    Return sb.ToString()
End Function

Private Function MaskEmail(email As String) As String
    Dim e As String = If(email, "").Trim()
    If e = "" Then Return "[VACIO]"
    Dim atPos As Integer = e.IndexOf("@"c)
    If atPos <= 1 Then Return "***" & e.Substring(Math.Max(0, atPos))
    Dim namePart As String = e.Substring(0, atPos)
    Dim domainPart As String = e.Substring(atPos)
    Return namePart.Substring(0, 1) & "***" & domainPart
End Function

'------------------------------ NORMALIZACION ------------------------------

Private Function NormalizeMaterialForArga(invMaterial As String, cat As HerinoxCatalog) As String
    Dim norm As String = NormalizeMaterialAlias(invMaterial)
    If String.IsNullOrEmpty(norm) Then norm = "A 36"

    ' 1) Intentar correlación contra nombres REALES de Herinox (crudos en DB).
    If cat IsNot Nothing AndAlso cat.Available AndAlso cat.RawMaterials IsNot Nothing AndAlso cat.RawMaterials.Count > 0 Then
        Dim rawMatch As String = TryMatchRawCatalogMaterial(invMaterial, cat.RawMaterials)
        If Not String.IsNullOrEmpty(rawMatch) Then
            Dim fromRaw As String = NormalizeMaterialAlias(rawMatch)
            If Not String.IsNullOrEmpty(fromRaw) Then
                norm = fromRaw
            End If
        End If
        ' También probar el alias ya canónico contra crudos (ej. "A 36").
        If String.Equals(norm, NormalizeMaterialAlias(invMaterial), StringComparison.OrdinalIgnoreCase) Then
            Dim raw2 As String = TryMatchRawCatalogMaterial(norm, cat.RawMaterials)
            If Not String.IsNullOrEmpty(raw2) Then
                Dim from2 As String = NormalizeMaterialAlias(raw2)
                If Not String.IsNullOrEmpty(from2) Then norm = from2
            End If
        End If
    End If

    ' 2) Si el catalogo tiene la variante canónica exacta, usarla.
    If cat IsNot Nothing AndAlso cat.Available AndAlso cat.CanonicalMaterials IsNot Nothing Then
        For Each m In cat.CanonicalMaterials
            If String.Equals(m.Trim(), norm.Trim(), StringComparison.OrdinalIgnoreCase) Then
                Return m
            End If
        Next
    End If

    ' 3) Nunca dejar nombres de librería Inventor (Acero Suave/Forjado/Genérico).
    Dim known As String = NormalizeMaterialAlias(norm)
    If Not String.IsNullOrEmpty(known) Then Return known
    Return "A 36"
End Function

Private Function TryMatchRawCatalogMaterial(invMaterial As String, rawMaterials As List(Of String)) As String
    If rawMaterials Is Nothing OrElse rawMaterials.Count = 0 Then Return ""
    Dim invKey As String = NormalizeLooseText(invMaterial)
    If invKey = "" Then Return ""

    For Each rawName In rawMaterials
        Dim rawKey As String = NormalizeLooseText(rawName)
        If rawKey = "" Then Continue For
        If String.Equals(invKey, rawKey, StringComparison.OrdinalIgnoreCase) Then
            Return rawName
        End If
    Next

    ' Fallback flexible por inclusión (ej. "Steel, Carbono ASTM A36" vs "Steel Carbon").
    For Each rawName In rawMaterials
        Dim rawKey As String = NormalizeLooseText(rawName)
        If rawKey = "" Then Continue For
        If invKey.Contains(rawKey) OrElse rawKey.Contains(invKey) Then
            Return rawName
        End If
    Next
    Return ""
End Function

Private Function NormalizeLooseText(raw As String) As String
    Dim t As String = UCase(Trim(CStr(raw)))
    t = Replace(t, "_", " ")
    t = Regex.Replace(t, "[^A-Z0-9]+", " ")
    t = Regex.Replace(t, "\s+", " ").Trim()
    Return t
End Function

Private Function NormalizeMaterialAlias(raw As String) As String
    Dim m As String = UCase(Trim(CStr(raw)))
    m = Replace(m, "_", " ")
    m = Regex.Replace(m, "\s+", " ")
    ' Quitar acentos (Genérico → GENERICO) para empatar Herinox.
    m = Replace(m, "Á", "A") : m = Replace(m, "É", "E") : m = Replace(m, "Í", "I")
    m = Replace(m, "Ó", "O") : m = Replace(m, "Ú", "U") : m = Replace(m, "Ü", "U")
    m = Replace(m, "Ñ", "N")

    If m = "" Then Return ""

    ' Galvanizado ANTES que A 36 genérico (si no, "A 36 GALV" caía en A 36).
    ' Nombre DXF "Galvanizado" → ANS GALVANIZADO; Herinox match vía A 36 GALV.
    If m.Contains("GALVAN") OrElse m.Contains("G90") OrElse m.Contains("HDG") _
       OrElse m.Contains("ZINCADO") OrElse m.Contains("GALVANNEAL") _
       OrElse (m.Contains("GALV") AndAlso (m.Contains("A 36") OrElse m.Contains("A36") OrElse m.Contains("ZINC"))) _
       OrElse (m.Contains("ZINC") AndAlso Not m.Contains("BRONZE")) Then
        Return "Galvanizado"
    End If

    If m.Contains("A 36") OrElse m.Contains("A36") OrElse m.Contains("ASTM A36") Then Return "A 36"

    ' Inventor ES: "Acero, Suave" / "Acero, Forjado" / Genérico — no están en Herinox.
    ' Empatar a A 36 (materia bruta carbono) para nest ANS.
    If m.Contains("SUAVE") OrElse m.Contains("FORJAD") OrElse m.Contains("MILD") _
       OrElse m.Contains("FORGED") OrElse m.Contains("GENERIC") OrElse m.Contains("GENERICO") _
       OrElse m = "DEFAULT" OrElse m.Contains("DEFAULT") Then
        Return "A 36"
    End If

    If m.Contains("CARBON") OrElse (m.Contains("ACERO") AndAlso m.Contains("CARBONO")) _
       OrElse m.Contains("STEEL, CARBON") OrElse m.Contains("STEEL CARBON") _
       OrElse m.Contains("MILD STEEL") OrElse m.Contains("HOT ROLLED") OrElse m.Contains("COLD ROLLED") _
       OrElse m = "CRS" OrElse m = "HRS" OrElse m.Contains(" HR ") OrElse m.StartsWith("HR ") _
       OrElse m.EndsWith(" HR") OrElse m.Contains("HRPO") Then
        Return "A 36"
    End If

    ' Cualquier "Acero…" de librería Inventor (no inox/al) → A 36.
    If m.Contains("ACERO") AndAlso Not (m.Contains("INOX") OrElse m.Contains("STAINLESS") OrElse m.Contains("ALUMIN")) Then
        Return "A 36"
    End If
    If (m.Contains("STEEL") AndAlso Not (m.Contains("STAINLESS") OrElse m.Contains("INOX") OrElse m.Contains("ALUMIN"))) _
       AndAlso Not m.Contains("TOOL") Then
        Return "A 36"
    End If

    If m.Contains("SSTL") AndAlso m.Contains("316") Then Return "SSTL 316"
    If m.Contains("316") AndAlso (m.Contains("SS") OrElse m.Contains("STAINLESS") OrElse m.Contains("INOX")) Then
        Return "SSTL 316"
    End If
    If m.Contains("SSTL") OrElse m.Contains("INOX") OrElse m.Contains("INOXIDABLE") OrElse m.Contains("STAINLESS") _
       OrElse (m.Contains("304") AndAlso (m.Contains("SS") OrElse m.Contains("STEEL"))) Then
        Return "SSTL 304"
    End If

    If m.Contains("ALUMIN") OrElse m.StartsWith("AL ") OrElse m = "AL" Then Return "Aluminio"

    Return ToTitleCaseSafe(m)
End Function

Private Function FormatThickness(v As Double) As String
    ' Compat: formateo crudo. Preferir FormatThicknessForArga en export.
    Return FmtInchDecimal(v)
End Function

' Tolerancia de empalme SM vs geometría (no exacto, sí "casi la misma medida").
Private Const THK_EMPATE_ABS_IN As Double = 0.01
Private Const THK_EMPATE_REL As Double = 0.03

Private Function ThicknessesEmpatan(smIn As Double, geoIn As Double) As Boolean
    If smIn <= 0 OrElse geoIn <= 0 Then Return False
    Dim d As Double = System.Math.Abs(smIn - geoIn)
    If d <= THK_EMPATE_ABS_IN Then Return True
    Dim ref As Double = smIn
    If geoIn > ref Then ref = geoIn
    If ref <= 0 Then Return False
    Return (d / ref) <= THK_EMPATE_REL
End Function

Private Function ResolvePartThicknessInches( _
    smDef As SheetMetalComponentDefinition, _
    part As PartDocument, _
    ByRef note As String, _
    ByRef warn As String, _
    ByRef marcarRevisarSm As Boolean _
) As Double
    ' Cal carpeta ANS = espesor real de placa.
    ' SM Thickness: si empata con geometría → Cal=SM.
    ' Si SM existe pero NO empata → Cal=geometría + [REVISAR SM] (Thickness mal en IPT).
    ' Si no hay SM → Cal=geometría + [REVISAR SM].
    note = ""
    warn = ""
    marcarRevisarSm = False
    Dim uom As UnitsOfMeasure = part.UnitsOfMeasure
    Dim smIn As Double = 0.0
    Try
        smIn = uom.ConvertUnits(smDef.Thickness.Value, UnitsTypeEnum.kDatabaseLengthUnits, UnitsTypeEnum.kInchLengthUnits)
    Catch
        smIn = 0.0
    End Try

    Dim geoIn As Double = 0.0
    Dim geoSrc As String = ""
    Try
        geoIn = MeasureGeometricThicknessInches(part, geoSrc)
    Catch
        geoIn = 0.0
        geoSrc = ""
    End Try
    Dim geoOk As Boolean = (geoIn >= 0.02 AndAlso geoIn <= 4.0)

    If smIn > 0 AndAlso geoOk Then
        If ThicknessesEmpatan(smIn, geoIn) Then
            note = "OK SM=" & FmtInchDecimal(smIn) & " ≈ geom=" & FmtInchDecimal(geoIn)
            Return smIn
        End If
        ' SM mal (ej. default Cal 11): nest con geo; marcar para corregir Thickness.
        marcarRevisarSm = True
        warn = "SM Thickness=" & FmtInchDecimal(smIn) & " ≠ pieza geom=" & FmtInchDecimal(geoIn) & _
               ". Cal ANS=" & FmtInchDecimal(geoIn) & " [REVISAR SM]; corrige Sheet Metal Defaults."
        note = "geom=" & FmtInchDecimal(geoIn) & " (SM IPT=" & FmtInchDecimal(smIn) & ")"
        Return geoIn
    End If

    If smIn > 0 Then
        ' Hay SM, sin geo fiable → Cal SM (bend deduction); sin marca.
        note = "SM=" & FmtInchDecimal(smIn)
        Return smIn
    End If

    marcarRevisarSm = True
    If geoOk Then
        warn = "Sin Sheet Metal Thickness; Cal por geometría=" & FmtInchDecimal(geoIn)
        note = "geom=" & FmtInchDecimal(geoIn) & If(geoSrc <> "", " [" & geoSrc & "]", "")
        Return geoIn
    End If

    Return 0.0
End Function

Private Function MeasureGeometricThicknessInches(part As PartDocument, ByRef src As String) As Double
    src = ""
    Dim uom As UnitsOfMeasure = part.UnitsOfMeasure
    ' 1) Caras paralelas = medida precisa del espesor de placa.
    Dim faceThk As Double = MeasureThicknessLargestParallelFaces(part, uom)
    If faceThk >= 0.02 AndAlso faceThk <= 4.0 Then
        src = "caras"
        Return faceThk
    End If

    ' 2) Fallback bbox (menos preciso; solo si no hay par de caras).
    Dim boxThk As Double = MeasureMinBodyExtentInches(part, uom)
    If boxThk >= 0.02 AndAlso boxThk <= 4.0 Then
        src = "bbox"
        Return boxThk
    End If
    Return 0.0
End Function

Private Function MeasureThicknessLargestParallelFaces(part As PartDocument, uom As UnitsOfMeasure) As Double
    Try
        Dim faceA As Face = GetLargestPlanarFace(part)
        If faceA Is Nothing Then Return 0.0
        Dim plnA As Plane = CType(faceA.Geometry, Plane)
        Dim nA As UnitVector = plnA.Normal
        Dim pA As Point = plnA.RootPoint

        Dim areaA As Double = faceA.Evaluator.Area
        Dim bestDistDb As Double = 0.0
        Dim found As Boolean = False
        Dim bodies As SurfaceBodies = part.ComponentDefinition.SurfaceBodies
        For Each body As SurfaceBody In bodies
            For Each faceB As Face In body.Faces
                If faceB Is faceA Then Continue For
                If faceB.SurfaceType <> SurfaceTypeEnum.kPlaneSurface Then Continue For
                ' Cara opuesta comparable (evita nervios / chaflanes chicos).
                If faceB.Evaluator.Area < (areaA * 0.35) Then Continue For
                Dim plnB As Plane = CType(faceB.Geometry, Plane)
                Dim nB As UnitVector = plnB.Normal
                Dim dot As Double = nA.X * nB.X + nA.Y * nB.Y + nA.Z * nB.Z
                ' Paralelas opuestas (caras de la placa).
                If dot > -0.98 Then Continue For
                Dim pB As Point = plnB.RootPoint
                Dim dx As Double = pB.X - pA.X
                Dim dy As Double = pB.Y - pA.Y
                Dim dz As Double = pB.Z - pA.Z
                Dim distDb As Double = System.Math.Abs(dx * nA.X + dy * nA.Y + dz * nA.Z)
                If distDb < 0.0001 Then Continue For
                If (Not found) OrElse distDb < bestDistDb Then
                    bestDistDb = distDb
                    found = True
                End If
            Next
        Next
        If Not found Then Return 0.0
        Return uom.ConvertUnits(bestDistDb, UnitsTypeEnum.kDatabaseLengthUnits, UnitsTypeEnum.kInchLengthUnits)
    Catch
        Return 0.0
    End Try
End Function

Private Function MeasureMinBodyExtentInches(part As PartDocument, uom As UnitsOfMeasure) As Double
    Try
        Dim minIn As Double = 1.0E9
        Dim any As Boolean = False
        Dim bodies As SurfaceBodies = part.ComponentDefinition.SurfaceBodies
        For Each body As SurfaceBody In bodies
            Dim box As Box = body.RangeBox
            Dim dx As Double = System.Math.Abs(box.MaxPoint.X - box.MinPoint.X)
            Dim dy As Double = System.Math.Abs(box.MaxPoint.Y - box.MinPoint.Y)
            Dim dz As Double = System.Math.Abs(box.MaxPoint.Z - box.MinPoint.Z)
            Dim mDb As Double = dx
            If dy < mDb Then mDb = dy
            If dz < mDb Then mDb = dz
            Dim mIn As Double = uom.ConvertUnits(mDb, UnitsTypeEnum.kDatabaseLengthUnits, UnitsTypeEnum.kInchLengthUnits)
            If mIn > 0 AndAlso mIn < minIn Then
                minIn = mIn
                any = True
            End If
        Next
        If any Then Return minIn
    Catch
    End Try
    Return 0.0
End Function

Private Function FormatThicknessForArga(thkIn As Double, materialName As String) As String
    ' Empata modules/herinox_sync.py + arga_gauge_equivalences.json.
    ' Nunca tumbar el export: si el snap falla, usa el decimal CAD formateado.
    Try
        If thkIn <= 0 Then Return FmtInchDecimal(0.0)
        Dim snapped As Double = SnapThicknessToArga(thkIn, materialName)
        If snapped <= 0 Then snapped = thkIn
        Return FmtInchDecimal(snapped)
    Catch
        Try
            Return FmtInchDecimal(thkIn)
        Catch
            Return "0"
        End Try
    End Try
End Function

Private Function FmtInchDecimal(v As Double) As String
    Try
        Dim txt As String = v.ToString("0.####", CultureInfo.InvariantCulture)
        If InStr(txt, ".") > 0 Then
            Do While Len(txt) > 1 AndAlso Right(txt, 1) = "0"
                txt = Left(txt, Len(txt) - 1)
            Loop
            If Right(txt, 1) = "." Then txt = Left(txt, Len(txt) - 1)
        End If
        If txt = "" OrElse txt = "-" Then Return "0"
        Return txt
    Catch
        Return "0"
    End Try
End Function

Private Function SnapThicknessToArga(thkIn As Double, materialName As String) As Double
    If thkIn <= 0 Then Return thkIn

    ' Placas gruesas / fracciones exactas (modo decimal Herinox).
    ' Si también hay gauge ≤0.008\", gana el más cercano (Cal 6 no cae en 0.188).
    Dim exacts(17) As Double
    exacts(0) = 0.1875 : exacts(1) = 0.188 : exacts(2) = 0.25
    exacts(3) = 0.3125 : exacts(4) = 0.375 : exacts(5) = 0.4375
    exacts(6) = 0.5 : exacts(7) = 0.5625 : exacts(8) = 0.625
    exacts(9) = 0.6875 : exacts(10) = 0.75 : exacts(11) = 0.875
    exacts(12) = 1.0 : exacts(13) = 1.125 : exacts(14) = 1.25
    exacts(15) = 1.5 : exacts(16) = 1.75 : exacts(17) = 2.0

    Dim bestExact As Double = -1.0
    Dim bestExactD As Double = 1.0E9
    Dim i As Integer
    For i = 0 To UBound(exacts)
        Dim de As Double = System.Math.Abs(thkIn - exacts(i))
        If de < bestExactD Then
            bestExactD = de
            bestExact = exacts(i)
        End If
    Next
    If bestExactD > 0.005 Then
        bestExact = -1.0
        bestExactD = 1.0E9
    End If

    Dim gauges() As Integer = Nothing
    Dim inches() As Double = Nothing
    FillGaugeTableForMaterial(materialName, gauges, inches)
    Dim bestGauge As Double = -1.0
    Dim bestGaugeD As Double = 1.0E9
    If gauges IsNot Nothing AndAlso inches IsNot Nothing AndAlso UBound(inches) >= 0 Then
        For i = 0 To UBound(inches)
            Dim dg As Double = System.Math.Abs(inches(i) - thkIn)
            If dg < bestGaugeD Then
                bestGaugeD = dg
                bestGauge = inches(i)
            End If
        Next
    End If
    ' Misma tolerancia que ANS (_nearest_steel_gauge ≈ 0.008").
    If bestGaugeD > 0.008 Then
        bestGauge = -1.0
        bestGaugeD = 1.0E9
    End If

    If bestExact >= 0 AndAlso bestGauge >= 0 Then
        If bestGaugeD <= bestExactD Then Return bestGauge
        Return bestExact
    End If
    If bestGauge >= 0 Then Return bestGauge
    If bestExact >= 0 Then Return bestExact
    Return thkIn
End Function

Private Sub FillGaugeTableForMaterial(materialName As String, ByRef gauges() As Integer, ByRef inches() As Double)
    ' Arrays fijos: más seguro en iLogic que Dictionary + For Each KeyValuePair.
    Dim m As String = UCase(Trim(CStr(materialName)))
    If m.Contains("SSTL") OrElse m.Contains("INOX") OrElse m.Contains("STAINLESS") Then
        gauges = New Integer() {10, 11, 12, 14, 16, 18, 20}
        inches = New Double() {0.1406, 0.125, 0.1094, 0.0781, 0.0625, 0.05, 0.0375}
        Exit Sub
    End If
    If m.Contains("ALUMIN") OrElse (Len(m) >= 3 AndAlso Left(m, 3) = "AL ") Then
        gauges = New Integer() {8, 9, 10, 11, 12, 13, 14, 15, 16, 17, 18, 19, 20}
        inches = New Double() {
            0.1285, 0.1144, 0.1019, 0.0907, 0.0808, 0.072, 0.0641,
            0.0571, 0.0508, 0.0453, 0.0403, 0.0359, 0.032
        }
        Exit Sub
    End If
    ' STEEL / Galvanizado / A 36 (herinox_sync.STEEL_GAUGE_TO_INCHES)
    gauges = New Integer() {3, 4, 5, 6, 7, 8, 9, 10, 11, 12, 13, 14, 15, 16, 18, 20}
    inches = New Double() {
        0.2391, 0.2242, 0.2092, 0.1943, 0.1793, 0.1644, 0.1495, 0.1345,
        0.1196, 0.1046, 0.0897, 0.0747, 0.0673, 0.0598, 0.0478, 0.0359
    }
End Sub

'------------------------------ UTILIDADES BASE ------------------------------

Private Function PickFolder(ByVal descr As String) As String
    Dim dlg As New FolderBrowserDialog()
    dlg.Description = descr
    dlg.ShowNewFolderButton = True
    If dlg.ShowDialog() = DialogResult.OK Then
        Return dlg.SelectedPath
    End If
    Return ""
End Function

Private Sub EnsureFlatPattern(smDef As SheetMetalComponentDefinition)
    If Not smDef.HasFlatPattern Then
        smDef.Unfold()
        smDef.FlatPattern.ExitEdit()
    End If
End Sub

Private Function EnsureFlatPatternHealthy(smDef As SheetMetalComponentDefinition) As Boolean
    ' False SOLO si Flat Pattern está realmente roto (cruz roja / no computa).
    ' No usar Edit/ExitEdit como prueba: falla en piezas sanas y marcaba TODO [REVISAR SM].
    Try
        EnsureFlatPattern(smDef)
    Catch
        Return False
    End Try
    Try
        If Not smDef.HasFlatPattern Then Return False
        Dim fp As FlatPattern = smDef.FlatPattern
        If fp Is Nothing Then Return False
        Try
            Dim hs As HealthStatusEnum = fp.HealthStatus
            If hs = HealthStatusEnum.kCannotComputeHealth OrElse _
               hs = HealthStatusEnum.kInErrorHealth OrElse _
               hs = HealthStatusEnum.kDeletedHealth Then
                Return False
            End If
        Catch
            ' Sin HealthStatus: si HasFlatPattern, asumir OK.
        End Try
        Return True
    Catch
        Return False
    End Try
End Function

Private Sub TrySetTopFace(smDef As SheetMetalComponentDefinition, Face As Face)
    Try
        smDef.FlatPattern.Edit()
        CallByName(smDef.FlatPattern, "SetASideFace", CallType.Method, Face)
        smDef.FlatPattern.ExitEdit()
        Exit Sub
    Catch
        Try
            smDef.FlatPattern.Edit()
            CallByName(smDef.FlatPattern, "SetTopFace", CallType.Method, Face)
            smDef.FlatPattern.ExitEdit()
            Exit Sub
        Catch
            Try
                CallByName(smDef, "SetASideFace", CallType.Method, Face)
                Exit Sub
            Catch
                ' Ignorar
            End Try
        End Try
    End Try
End Sub

Private Sub ExportFlatPatternDXF(pDoc As PartDocument, dxfFullname As String)
    Dim smDef As SheetMetalComponentDefinition = CType(pDoc.ComponentDefinition, SheetMetalComponentDefinition)
    EnsureFlatPattern(smDef)
    Dim fp As FlatPattern = smDef.FlatPattern
    Dim fmt As String = "FLAT PATTERN DXF?AcadVersion=2000"

    Try
        fp.DataIO.WriteDataToFile(fmt, dxfFullname)
    Catch ex As System.Exception
        Dim addin As TranslatorAddIn = CType(ThisApplication.ApplicationAddIns.ItemById("{C24E3AC4-122E-11D5-8E91-0010B541CD80}"), TranslatorAddIn)
        Dim ctx As TranslationContext = ThisApplication.TransientObjects.CreateTranslationContext()
        ctx.Type = IOMechanismEnum.kFileBrowseIOMechanism
        Dim opts As NameValueMap = ThisApplication.TransientObjects.CreateNameValueMap()
        Dim data As DataMedium = ThisApplication.TransientObjects.CreateDataMedium()
        data.FileName = dxfFullname
        If addin.HasSaveCopyAsOptions(pDoc, ctx, opts) Then
            ' opts.Value("Export_Acad_IniFile") = "C:\Ruta\a\DXFEXPORT.ini"
        End If
        addin.SaveCopyAs(pDoc, ctx, opts, data)
    End Try
End Sub

Private Function SafeMaterialName(smDef As SheetMetalComponentDefinition, pDoc As PartDocument) As String
    Dim name As String = ""
    Try
        name = smDef.Material.Name
    Catch
        Try
            name = CStr(pDoc.PropertySets.Item("Design Tracking Properties").Item("Material").Value)
        Catch
        End Try
    End Try
    If String.IsNullOrWhiteSpace(name) Then name = "Material"
    Return name
End Function

Private Function GetLargestPlanarFace(part As PartDocument) As Face
    Dim largestArea As Double = 0
    Dim largestFace As Face = Nothing

    Dim surfBodies As SurfaceBodies = part.ComponentDefinition.SurfaceBodies
    For Each body As SurfaceBody In surfBodies
        For Each face As Face In body.Faces
            If Face.SurfaceType = SurfaceTypeEnum.kPlaneSurface Then
                Dim area As Double = Face.Evaluator.Area
                If area > largestArea Then
                    largestArea = area
                    largestFace = Face
                End If
            End If
        Next
    Next
    Return largestFace
End Function

'------------------------------ HELPERS ------------------------------

Private Function JsonEscape(s As String) As String
    Dim t As String = If(s, "")
    t = t.Replace("\", "\\")
    t = t.Replace("""", "\""")
    Return t
End Function

Private Function JsonGetString(raw As String, key As String) As String
    Try
        If String.IsNullOrEmpty(raw) Then Return ""
        Dim pattern As String = """" & Regex.Escape(key) & """\s*:\s*(?:""(?<v>[^""]*)""|(?<n>[-+]?\d+(\.\d+)?)|(?<b>true|false))"
        Dim m As Match = Regex.Match(raw, pattern, RegexOptions.IgnoreCase)
        If Not m.Success Then Return ""
        If m.Groups("v").Success Then Return m.Groups("v").Value
        If m.Groups("n").Success Then Return m.Groups("n").Value
        If m.Groups("b").Success Then Return m.Groups("b").Value
    Catch
    End Try
    Return ""
End Function

Private Function GetCfg(cfg As Dictionary(Of String, String), key As String, defVal As String) As String
    If cfg Is Nothing Then Return defVal
    If cfg.ContainsKey(key) Then
        Dim v As String = cfg(key)
        If Not String.IsNullOrEmpty(v) Then Return v
    End If
    Return defVal
End Function

Private Function SafeInt(s As String, defVal As Integer) As Integer
    Try
        Return CInt(Math.Round(CDbl(s), 0))
    Catch
        Return defVal
    End Try
End Function

Private Function ToTitleCaseSafe(raw As String) As String
    Try
        Dim ti As TextInfo = CultureInfo.InvariantCulture.TextInfo
        Return ti.ToTitleCase(LCase(raw))
    Catch
        Return raw
    End Try
End Function

Private Function SanitizeForPath(s As String) As String
    Dim t As String = If(s, "")
    Dim bad() As Char = System.IO.Path.GetInvalidPathChars()
    For Each c As Char In bad
        t = t.Replace(c, "_"c)
    Next
    t = t.Replace(":", " -")
    t = t.Replace("?", "")
    t = t.Replace("*", "")
    t = t.Replace("""", "")
    t = t.Replace("<", "")
    t = t.Replace(">", "")
    t = t.Replace("|", "")
    t = Regex.Replace(t, "\s+", " ").Trim()
    Return t
End Function

Private Function SanitizeForFileName(s As String) As String
    Dim t As String = If(s, "")
    Dim bad() As Char = System.IO.Path.GetInvalidFileNameChars()
    For Each c As Char In bad
        t = t.Replace(c, "_"c)
    Next
    t = Regex.Replace(t, "\s+", " ").Trim()
    Return t
End Function
